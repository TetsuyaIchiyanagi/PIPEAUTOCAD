;; 空の使い捨て図面でAPPLOADし、XXPTESTを実行する。
;; 実行後は保存せずに閉じること。通常の作業図面では実行を拒否する。
(vl-load-com)

(defun XXP-test-check (condition message)
  (if condition
    (progn (setq XXP-passed (1+ XXP-passed)) (princ (strcat "\nPASS: " message)))
    (progn (setq XXP-failed (1+ XXP-failed)) (princ (strcat "\nFAIL: " message)))))

(defun c:XXPATTRCHECK (/ XXP-passed XXP-failed visible hidden definition constant result)
  ;; 図面・ActiveX不要の属性振り分け試験。Core Consoleでも実行できる。
  (setq XXP-passed 0 XXP-failed 0
        visible '((0 . "ATTRIB") (2 . "TAG") (1 . "USER-42") (70 . 0) (10 1.0 2.0 0.0))
        hidden '((0 . "ATTRIB") (2 . "HIDDEN") (1 . "SECRET-42") (70 . 1))
        definition '((0 . "ATTDEF") (2 . "tag") (1 . "DEFAULT") (70 . 0))
        constant '((0 . "ATTDEF") (2 . "CONST") (1 . "FIXED") (70 . 2)))
  (setq result (XXP-attribute-plan (list visible) (list definition)))
  (XXP-test-check (equal (car result) (list visible)) "actual value and geometry override default, case-insensitive tag")
  (XXP-test-check (= "USER-42" (cdr (assoc 1 (caar result)))) "value retained instead of tag")
  (setq result (XXP-attribute-plan (list hidden)
                 '(((0 . "ATTDEF") (2 . "HIDDEN") (1 . "DEFAULT") (70 . 0)))))
  (XXP-test-check (and (null (car result)) (= 1 (cadr result))) "hidden reference leaves no text or default")
  (setq result (XXP-attribute-plan nil
                 '(((0 . "ATTDEF") (2 . "HIDDEN") (1 . "SECRET") (70 . 3)))))
  (XXP-test-check (and (null (car result)) (= 1 (cadr result))) "hidden constant definition removed")
  (setq result (XXP-attribute-plan (list visible hidden) (list definition constant)))
  (XXP-test-check (and (equal (car result) (list visible constant)) (= 1 (cadr result)))
                  "visible values only, constant kept once")
  (setq result (XXP-attribute-plan (list visible) (list (subst '(70 . 2) '(70 . 0) definition))))
  (XXP-test-check (= 1 (length (car result))) "matched constant is not duplicated")
  (XXP-test-check (not (XXP-invisible-p '((70 . 4)))) "unrelated attribute flags do not hide text")
  (XXP-test-check (equal '(nil 0) (XXP-attribute-plan nil nil)) "no attributes leaves no text")
  (princ (strcat "\nXXPATTRCHECK: PASS=" (itoa XXP-passed) " FAIL=" (itoa XXP-failed)))
  (princ))

(defun XXP-test-process (objects / selection object)
  (setq selection (ssadd))
  (foreach object objects (ssadd (vlax-vla-object->ename object) selection))
  (XXP-process selection))

(defun XXP-test-block (name / block)
  (setq block (vla-Add (vla-get-Blocks XXP-doc) (vlax-3d-point '(0 0 0)) name))
  (vla-AddLine block (vlax-3d-point '(0 0 0)) (vlax-3d-point '(10 0 0)))
  block)

(defun XXP-test-insert (space name sx sy angle)
  (vla-InsertBlock space (vlax-3d-point '(20 30 0)) name sx sy 1.0 angle))

(defun c:XXPTEST (/ *error* XXP-doc XXP-marker XXP-owner XXP-reason XXP-passed XXP-failed
                   space blocks block reference entity result marker generated next props text-data
                   objects angle scale data codes code expected found layer poly points undo values)
  (defun *error* (message)
    (vl-catch-all-apply 'XXP-rollback nil)
    (if undo (vl-catch-all-apply 'vla-EndUndoMark (list XXP-doc)))
    (princ (strcat "\nXXPTEST ERROR: " message)) (princ))
  (setq XXP-doc (vla-get-ActiveDocument (vlax-get-acad-object))
        space (vla-get-ModelSpace XXP-doc) blocks (vla-get-Blocks XXP-doc)
        XXP-passed 0 XXP-failed 0)
  (if (or (> (vla-get-Count space) 0) (tblsearch "BLOCK" "XXP_TEST_BASE"))
    (princ "\nXXPTEST：空の使い捨て図面を開いてください。")
    (progn
      (vla-StartUndoMark XXP-doc) (setq undo T)
      (XXP-test-block "XXP_TEST_BASE")
      (setq reference (XXP-test-insert space "XXP_TEST_BASE" 1.0 1.0 0.0)
            entity (vlax-vla-object->ename reference)
            result (XXP-test-process (list reference)))
      (XXP-test-check (and (= 1 (car result)) (null (entget entity))) "normal block")
      (setq next "XXP_TEST_BASE")
      (foreach text-data '("XXP_TEST_N1" "XXP_TEST_N2" "XXP_TEST_N3")
        (setq block (vla-Add blocks (vlax-3d-point '(0 0 0)) text-data))
        (XXP-test-insert block next 1.0 1.0 0.0)
        (setq next text-data))
      (setq result (XXP-test-process (list (XXP-test-insert space next 1.0 1.0 0.0))))
      (XXP-test-check (= 4 (car result)) "three nested levels")
      (setq points (vlax-make-safearray vlax-vbDouble '(0 . 5)))
      (vlax-safearray-fill points '(0.0 0.0 10.0 0.0 10.0 10.0))
      (setq poly (vla-AddLightWeightPolyline space points))
      (vla-SetBulge poly 1 0.5)
      (setq marker (XXP-tail) result (XXP-test-process (list poly))
            generated (XXP-new-entities marker (vlax-vla-object->ename space)))
      (XXP-test-check (and (= 1 (car result)) (= 2 (length generated))
                          (member "ARC" (mapcar '(lambda (e) (cdr (assoc 0 (entget e)))) generated)))
                      "polyline to LINE/ARC")
      (setq block (XXP-test-block "XXP_TEST_ATTR"))
      (vla-AddAttribute block 2.5 0 "Visible" (vlax-3d-point '(1 2 0)) "VISIBLE" "VALUE")
      (vla-AddAttribute block 2.5 1 "Hidden" (vlax-3d-point '(1 5 0)) "HIDDEN" "SECRET")
      (vla-AddAttribute block 2.5 2 "Constant" (vlax-3d-point '(1 8 0)) "CONSTANT" "FIXED")
      (foreach scale '(1.0 2.0 -1.0)
        (setq reference (XXP-test-insert space "XXP_TEST_ATTR" scale 1.5 0.7))
        ;; 定義の既定値と異なる参照値を設定し、値が保持されることを確認する。
        (foreach next (vlax-invoke reference 'GetAttributes)
          (vla-put-TextString next
            (if (= "VISIBLE" (vla-get-TagString next)) "REF-42" "HIDDEN-42")))
        (setq entity (vlax-vla-object->ename reference)
              props (vl-remove-if 'XXP-invisible-p (XXP-attributes entity))
              expected (car props) marker (XXP-tail)
              result (XXP-test-process (list reference))
              generated (XXP-new-entities marker (vlax-vla-object->ename space)) found nil values nil)
        (foreach next generated
          (setq data (entget next))
          (if (= "TEXT" (cdr (assoc 0 data)))
            (setq values (cons (cdr (assoc 1 data)) values)))
          (if (and (= "TEXT" (cdr (assoc 0 data))) (= "REF-42" (cdr (assoc 1 data))))
            (setq found (cons data found))))
        (XXP-test-check (and (= 1 (car result)) (= 1 (cadr result)) (= 1 (length found)))
                        (strcat "attributes visible/hidden/dedup scale=" (rtos scale 2 1)))
        (XXP-test-check
          (and (= 2 (length values)) (member "REF-42" values) (member "FIXED" values)
               (not (vl-some '(lambda (e) (= "ATTDEF" (cdr (assoc 0 (entget e))))) generated)))
          (strcat "actual values only; hidden values and tags absent scale=" (rtos scale 2 1)))
        (setq data (car found) codes '(10 11 40 50 41 51 7 71 72 210) found T)
        (foreach code codes
          (if (not (equal (cdr (assoc code expected)) (cdr (assoc code data)) 1e-8))
            (setq found nil)))
        (XXP-test-check found (strcat "attribute geometry/style scale=" (rtos scale 2 1))))
      (setq block (XXP-test-block "XXP_TEST_NESTED_ATTR")
            reference (XXP-test-insert block "XXP_TEST_ATTR" 1.0 1.0 0.0))
      (foreach next (vlax-invoke reference 'GetAttributes)
        (vla-put-TextString next
          (if (= "VISIBLE" (vla-get-TagString next)) "NESTED-42" "NESTED-HIDDEN")))
      (setq reference (XXP-test-insert space "XXP_TEST_NESTED_ATTR" 1.0 1.0 0.0)
            marker (XXP-tail) result (XXP-test-process (list reference))
            generated (XXP-new-entities marker (vlax-vla-object->ename space)) values nil)
      (foreach next generated
        (setq data (entget next))
        (if (= "TEXT" (cdr (assoc 0 data))) (setq values (cons (cdr (assoc 1 data)) values))))
      (XXP-test-check (and (= 2 (car result)) (= 1 (cadr result))
                           (= 2 (length values)) (member "NESTED-42" values) (member "FIXED" values))
                      "nested actual value retained; hidden attribute removed")
      (setq block (vla-Add blocks (vlax-3d-point '(0 0 0)) "XXP_TEST_HIDDEN_ONLY"))
      (vla-AddAttribute block 2.5 1 "Hidden only" (vlax-3d-point '(1 2 0)) "HIDDEN_ONLY" "NO_TEXT")
      (setq reference (XXP-test-insert space "XXP_TEST_HIDDEN_ONLY" 1.0 1.0 0.0)
            entity (vlax-vla-object->ename reference) marker (XXP-tail)
            result (XXP-test-process (list reference)))
      (XXP-test-check (and (= 1 (car result)) (= 1 (cadr result)) (null (entget entity))
                           (null (XXP-new-entities marker (vlax-vla-object->ename space))))
                      "hidden-only block leaves no text or definitions")
      (setq block (XXP-test-block "XXP_TEST_DENY"))
      (vla-put-Explodable block :vlax-false)
      (setq reference (XXP-test-insert space "XXP_TEST_DENY" 1.0 1.0 0.0)
            entity (vlax-vla-object->ename reference) result (XXP-test-process (list reference)))
      (XXP-test-check (and (= 1 (caddr result)) (entget entity)) "non-explodable preserved")
      (setq layer (vla-Add (vla-get-Layers XXP-doc) "XXP_TEST_LOCK")
            reference (XXP-test-insert space "XXP_TEST_BASE" 1.0 1.0 0.0)
            entity (vlax-vla-object->ename reference))
      (vla-put-Layer reference "XXP_TEST_LOCK") (vla-put-Lock layer :vlax-true)
      (setq result (XXP-test-process (list reference)))
      (XXP-test-check (and (= 1 (caddr result)) (entget entity)) "locked layer preserved")
      (vla-put-Lock layer :vlax-false)
      (setq objects (list (XXP-test-insert space "XXP_TEST_BASE" 1.0 1.0 0.0)
                          (XXP-test-insert space "XXP_TEST_BASE" 1.0 1.0 0.0))
            result (XXP-test-process objects))
      (XXP-test-check (= 2 (car result)) "multiple selection")
      (vla-EndUndoMark XXP-doc) (setq undo nil)
      (princ (strcat "\nXXPTEST: PASS=" (itoa XXP-passed) " FAIL=" (itoa XXP-failed)))
      (princ "\n残りの手動試験はXXPLODE.mdを参照。図面は保存せず閉じてください。")))
  (princ))
(princ)
