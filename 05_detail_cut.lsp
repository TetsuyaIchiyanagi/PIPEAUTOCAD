;; DETAILCUT - Windows AutoCAD / Visual LISP ActiveX.
;; Standalone loadable. See DETAILCUT.md for limits and verification status.
(vl-load-com)

(defun dc:track (o)
  ;; Keep entity names, not COM wrappers that remain after Delete/Explode.
  (setq dc:made (cons (vlax-vla-object->ename o) dc:made)) o)
(defun dc:del (o / e r)
  (setq r (vl-catch-all-apply 'vlax-vla-object->ename (list o)))
  (if (and (not (vl-catch-all-error-p r)) (setq e r) (entget e))
    (vla-Delete o)))
(defun dc:cleanup (/ e)
  (foreach e dc:made
    (if (entget e)
      (vl-catch-all-apply 'entdel (list e)))))
(defun dc:stage (label e / d)
  (setq dc:step label dc:entity-info "")
  (if (and e (setq d (entget e)))
    (setq dc:entity-info (strcat " / " (cdr (assoc 0 d)) " handle=" (cdr (assoc 5 d))))))
(defun dc:fail (s) (setq dc:reason s) (exit))
(defun dc:array (v / a r) (setq a (vlax-variant-value v)) (if (> (vlax-safearray-get-u-bound a 1) -1) (vlax-safearray->list a)))
(defun dc:point (o p / pt)
  (setq pt (vlax-curve-getPointAtParam o p))
  (if (null pt)
    (dc:fail (strcat "Curve point unavailable at parameter " (rtos p 2 12))))
  (trans pt 0 1))
(defun dc:inside (p)
  (and (<= (- dc:x0 dc:eps) (car p) (+ dc:x1 dc:eps))
       (<= (- dc:y0 dc:eps) (cadr p) (+ dc:y1 dc:eps))))
(defun dc:overlap (o / lo hi pts x y z p xs ys)
  (vla-GetBoundingBox o 'lo 'hi)
  (setq lo (vlax-safearray->list lo) hi (vlax-safearray->list hi))
  (foreach x (list (car lo) (car hi))
    (foreach y (list (cadr lo) (cadr hi))
      (foreach z (list (caddr lo) (caddr hi))
        (setq p (trans (list x y z) 0 1) xs (cons (car p) xs) ys (cons (cadr p) ys)))))
  (setq dc:contained (and (>= (apply 'min xs) dc:x0) (<= (apply 'max xs) dc:x1)
                          (>= (apply 'min ys) dc:y0) (<= (apply 'max ys) dc:y1)))
  (and (<= (apply 'min xs) dc:x1) (>= (apply 'max xs) dc:x0)
       (<= (apply 'min ys) dc:y1) (>= (apply 'max ys) dc:y0)))
(defun dc:issue (s / a)
  (if (setq a (assoc s dc:issues))
    (setq dc:issues (subst (cons s (1+ (cdr a))) a dc:issues))
    (setq dc:issues (cons (cons s 1) dc:issues))))
(defun dc:properties (e / d)
  (setq d (entget e))
  (vl-remove-if-not '(lambda (a) (member (car a) '(8 6 48 62 420 430 440 370 39))) d))
(defun dc:poly (verts closed props / normal p data e v)
  (setq normal (trans '(0.0 0.0 1.0) 1 0 T)
        p (trans (trans (caar verts) 1 0) 0 normal)
        data (append (list '(0 . "LWPOLYLINE") '(100 . "AcDbEntity")) props
               (list '(100 . "AcDbPolyline") (cons 90 (length verts))
                     (cons 70 (if closed 1 0)) (cons 38 (caddr p)) (cons 210 normal))))
  (foreach v verts
    (setq p (trans (trans (car v) 1 0) 0 normal)
          data (append data (list (cons 10 (list (car p) (cadr p)))
                                 (cons 42 (cadr v)) (cons 40 (caddr v)) (cons 41 (cadddr v))))))
  (if (setq e (entmakex data)) (dc:track (vlax-ename->vla-object e))
    (dc:fail "Cannot create polyline (check current layer/space).")))
(defun dc:widths (e / d typ out a sw ew vertex)
  (setq d (entget e) typ (cdr (assoc 0 d)))
  (cond
    ((= typ "LWPOLYLINE")
      (setq sw 0.0 ew 0.0)
      (foreach a d
        (cond ((= (car a) 10) (if vertex (setq out (cons (list sw ew) out)))
                                      (setq vertex T sw 0.0 ew 0.0))
              ((= (car a) 40) (setq sw (cdr a)))
              ((= (car a) 41) (setq ew (cdr a)))))
      (if vertex (setq out (cons (list sw ew) out)))
      (setq out (reverse out))
      (if (and (assoc 43 d) (> (cdr (assoc 43 d)) 0.0))
        (setq out (mapcar '(lambda (a) (list (cdr (assoc 43 d)) (cdr (assoc 43 d)))) out))))
    ((= typ "POLYLINE")
      (setq vertex (entnext e))
      (while (= "VERTEX" (cdr (assoc 0 (setq d (entget vertex)))))
        (setq out (cons (list (cond ((cdr (assoc 40 d))) (0.0))
                                  (cond ((cdr (assoc 41 d))) (0.0))) out)
              vertex (entnext vertex)))
      (setq out (reverse out))))
  out)
(defun dc:unique (values / out x)
  (foreach x (vl-sort values '<)
    (if (or (null out) (> (abs (- x (car out))) 1e-9)) (setq out (cons x out))))
  (reverse out))
;; Intersections are computed in the actual curve plane, with UCS-aligned edges.
(defun dc:params (o / start end z corners edges a b edge raw p q vals i pair)
  (setq start (vlax-curve-getStartParam o) end (vlax-curve-getEndParam o)
        vals (list start end) z (caddr (dc:point o start))
        corners (list (list dc:x0 dc:y0 z) (list dc:x1 dc:y0 z)
                      (list dc:x1 dc:y1 z) (list dc:x0 dc:y1 z)))
  (setq i (1+ (fix start)))
  (while (< i end) (setq vals (cons (float i) vals) i (1+ i)))
  ;; Also split circles/arcs into at most quarter turns for stable bulges.
  (if (member (vla-get-ObjectName o) '("AcDbCircle" "AcDbArc"))
    (progn (setq i 1) (repeat 3 (setq vals (cons (+ start (* (/ (- end start) 4.0) i)) vals) i (1+ i)))))
  (foreach pair (mapcar 'list corners (append (cdr corners) (list (car corners))))
    (setq edge (dc:track (vla-AddLine dc:space (vlax-3d-point (trans (car pair) 1 0))
                                            (vlax-3d-point (trans (cadr pair) 1 0))))
          raw (dc:array (vla-IntersectWith o edge 0)))
    (while raw
      (setq p (list (car raw) (cadr raw) (caddr raw)) raw (cdddr raw)
            q (vlax-curve-getParamAtPoint o (vlax-curve-getClosestPointTo o p)))
      (if q (setq vals (cons q vals))))
    (dc:del edge))
  (dc:unique vals))
(defun dc:vertex (o a b widths / p q m dx dy len2 bulge w f g)
  (setq p (dc:point o a) q (dc:point o b) m (dc:point o (/ (+ a b) 2.0))
        dx (- (car q) (car p)) dy (- (cadr q) (cadr p)) len2 (+ (* dx dx) (* dy dy))
        bulge (if (> len2 (* dc:eps dc:eps))
                (/ (* -2.0 (- (* dx (- (cadr m) (cadr p))) (* dy (- (car m) (car p))))) len2) 0.0)
        ;; LINE / ARC / CIRCLE have no polyline vertex-width list.
        ;; Never pass that nil list to nth in AutoLISP.
        w (if widths (nth (fix (+ a 1e-10)) widths) '(0.0 0.0)))
  (if (null w) (setq w '(0.0 0.0)))
  (setq f (- a (fix (+ a 1e-10))) g (- b (fix (+ a 1e-10))))
  (list p bulge (+ (car w) (* f (- (cadr w) (car w))))
                 (+ (car w) (* g (- (cadr w) (car w))))))
(defun dc:clip (o / e ps widths groups run a b lastp allin props result g)
  (setq e (vlax-vla-object->ename o))
  (dc:stage "Calculate boundary intersections" e)
  (setq ps (dc:params o))
  (dc:stage "Read curve widths and properties" e)
  (setq widths (dc:widths e)
        props (dc:properties e) allin T)
  (dc:stage "Build clipped curve intervals" e)
  (while (cdr ps)
    (setq a (car ps) b (cadr ps))
    (if (and (dc:inside (dc:point o (/ (+ a b) 2.0)))
             (> (- (vlax-curve-getDistAtParam o b) (vlax-curve-getDistAtParam o a)) dc:eps))
      (setq run (append run (list (dc:vertex o a b widths))) lastp (dc:point o b))
      (progn (setq allin nil)
        (if run (setq groups (cons (append run (list (list lastp 0.0 0.0 0.0))) groups) run nil))))
    (setq ps (cdr ps)))
  (if run (setq groups (cons (append run (list (list lastp 0.0 0.0 0.0))) groups)))
  (if allin (list o)
    (progn
      (dc:stage "Create clipped polylines" e)
      (foreach g (reverse groups) (setq result (cons (dc:poly g nil props) result)))
      (dc:del o) result)))
(defun dc:planar (o / d n p q)
  (setq d (entget (vlax-vla-object->ename o)) n (cdr (assoc 210 d)))
  (if (null n) (setq n '(0.0 0.0 1.0)))
  (setq n (trans n 0 1 T) p (dc:point o (vlax-curve-getStartParam o))
        q (dc:point o (vlax-curve-getEndParam o)))
  (and (< (abs (- (caddr p) (caddr q))) dc:eps)
       (or (= (cdr (assoc 0 d)) "LINE")
           (and (< (abs (car n)) 1e-8) (< (abs (cadr n)) 1e-8)))))
;; Resolve common ByBlock inheritance before processing exploded children.
(defun dc:inherit (child parent /)
  (if (= "0" (vla-get-Layer child)) (vla-put-Layer child (vla-get-Layer parent)))
  (if (= 0 (vla-get-Color child)) (vla-put-TrueColor child (vla-get-TrueColor parent)))
  (if (= "BYBLOCK" (strcase (vla-get-Linetype child)))
    (vla-put-Linetype child (vla-get-Linetype parent)))
  (if (= -2 (vla-get-Lineweight child)) (vla-put-Lineweight child (vla-get-Lineweight parent))))
;; Liang-Barsky interval clipping in UCS. No AutoCAD curve API is used.
(defun dc:line-interval (a b / dx dy low high valid pair den num ratio)
  (setq dx (- (car b) (car a)) dy (- (cadr b) (cadr a))
        low 0.0 high 1.0 valid T)
  (foreach pair (list (list (- dx) (- (car a) dc:x0))
                      (list dx (- dc:x1 (car a)))
                      (list (- dy) (- (cadr a) dc:y0))
                      (list dy (- dc:y1 (cadr a))))
    (setq den (car pair) num (cadr pair))
    (if (= den 0.0)
      (if (< num (- dc:eps)) (setq valid nil))
      (progn
        (setq ratio (/ num den))
        (if (< den 0.0) (setq low (max low ratio)) (setq high (min high ratio))))))
  (if (and valid (<= low high)) (list low high)))
(defun dc:lerp (a b ratio)
  (mapcar '(lambda (x y) (+ x (* ratio (- y x)))) a b))
(defun dc:clip-line (o / e d a b interval p q updated)
  (setq e (vlax-vla-object->ename o) d (entget e)
        a (trans (cdr (assoc 10 d)) 0 1) b (trans (cdr (assoc 11 d)) 0 1))
  (dc:stage "Clip LINE from DXF endpoints" e)
  (cond
    ((or (> (abs (- (caddr a) (caddr b))) dc:eps)
         (and (assoc 39 d) (/= 0.0 (cdr (assoc 39 d)))))
      (dc:issue "LINE (3D/thickness)") nil)
    ((<= (distance a b) dc:eps) (dc:del o) nil)
    ((and (dc:inside a) (dc:inside b)) (list o))
    ((setq interval (dc:line-interval a b))
      (setq p (dc:lerp a b (car interval)) q (dc:lerp a b (cadr interval)))
      (if (<= (distance p q) dc:eps)
        (progn (dc:del o) nil)
        (progn
          ;; Only change endpoints of the tracked copy. Keep LINE properties.
          (setq updated (subst (cons 10 (trans p 1 0)) (assoc 10 d) d)
                updated (subst (cons 11 (trans q 1 0)) (assoc 11 updated) updated))
          (if (null (entmod updated)) (dc:fail "Cannot update copied LINE endpoints."))
          (list o))))
    (T (dc:del o) nil)))
;; Clip a polygon against one axis-aligned half-plane (Sutherland-Hodgman).
(defun dc:polygon-edge (points axis bound lower / prev curr pin cin ratio hit out)
  (if points
    (progn
      (setq prev (last points))
      (foreach curr points
        (setq pin (if lower (>= (nth axis prev) bound) (<= (nth axis prev) bound))
              cin (if lower (>= (nth axis curr) bound) (<= (nth axis curr) bound)))
        (if (not (eq pin cin))
          (progn
            (setq ratio (/ (- bound (nth axis prev)) (- (nth axis curr) (nth axis prev)))
                  hit (dc:lerp prev curr ratio) out (cons hit out))))
        (if cin (setq out (cons curr out)))
        (setq prev curr))))
  (reverse out))
(defun dc:polygon-clip (points)
  (setq points (dc:polygon-edge points 0 dc:x0 T)
        points (dc:polygon-edge points 0 dc:x1 nil)
        points (dc:polygon-edge points 1 dc:y0 T)
        points (dc:polygon-edge points 1 dc:y1 nil)))
(defun dc:solid-triangle (a b c props / normal pts data e area)
  (setq area (abs (- (* (- (car b) (car a)) (- (cadr c) (cadr a)))
                    (* (- (cadr b) (cadr a)) (- (car c) (car a))))))
  (if (> area (* dc:eps dc:eps))
    (progn
      (setq normal (trans '(0.0 0.0 1.0) 1 0 T)
            pts (mapcar '(lambda (p) (trans (trans p 1 0) 0 normal)) (list a b c))
            data (append '((0 . "SOLID") (100 . "AcDbEntity")) props
                   (list '(100 . "AcDbTrace") (cons 10 (car pts)) (cons 11 (cadr pts))
                         (cons 12 (caddr pts)) (cons 13 (caddr pts)) (cons 210 normal))))
      (if (setq e (entmakex data)) (dc:track (vlax-ename->vla-object e))
        (dc:fail "Cannot create clipped SOLID.")))))
(defun dc:clip-solid (o / e d points flat inside z p triangles triangle poly anchor tail made result props)
  (setq e (vlax-vla-object->ename o) d (entget e) flat T inside T
        points (mapcar '(lambda (code) (trans (trans (cdr (assoc code d)) e 0) 0 1)) '(10 11 12 13))
        z (caddr (car points)) props (dc:properties e))
  (dc:stage "Clip SOLID polygon" e)
  (foreach p points
    (if (> (abs (- (caddr p) z)) dc:eps) (setq flat nil))
    (if (not (dc:inside p)) (setq inside nil)))
  (cond
    ((or (not flat) (and (assoc 39 d) (/= (cdr (assoc 39 d)) 0.0)))
      (dc:issue "SOLID (3D/thickness)") nil)
    (inside (list o))
    (T
      ;; DXF's quad perimeter is 10,11,13,12; use its two triangles.
      (setq triangles (list (list (nth 0 points) (nth 1 points) (nth 2 points))
                            (list (nth 1 points) (nth 3 points) (nth 2 points))))
      (foreach triangle triangles
        (setq poly (dc:polygon-clip triangle))
        (if (>= (length poly) 3)
          (progn
            (setq anchor (car poly) tail (cdr poly))
            (while (cdr tail)
              (if (setq made (dc:solid-triangle anchor (car tail) (cadr tail) props))
                (setq result (cons made result)))
              (setq tail (cdr tail))))))
      (dc:del o) result)))
;; Ellipse DXF geometry: WCS center, major-axis vector, normal and ratio.
;; Solve each rectangular boundary analytically; keep true ELLIPSE entities.
(defun dc:cross (a b)
  (list (- (* (cadr a) (caddr b)) (* (caddr a) (cadr b)))
        (- (* (caddr a) (car b)) (* (car a) (caddr b)))
        (- (* (car a) (cadr b)) (* (cadr a) (car b)))))
(defun dc:ellipse-point (center major minor param)
  (mapcar '(lambda (c a b) (+ c (* a (cos param)) (* b (sin param)))) center major minor))
(defun dc:ellipse-roots (a b offset start end / radius value phase angle k param roots)
  (setq radius (sqrt (+ (* a a) (* b b))))
  (if (> radius 0.0)
    (progn
      (setq value (/ offset radius))
      (if (<= (abs value) 1.0)
        (progn
          (setq phase (atan b a) angle (atan (sqrt (max 0.0 (- 1.0 (* value value)))) value) k -2)
          (repeat 7
            (foreach param (list (+ phase angle (* k 2.0 pi)) (+ phase (- angle) (* k 2.0 pi)))
              (if (and (> param start) (< param end)) (setq roots (cons param roots))))
            (setq k (1+ k)))))))
  roots)
(defun dc:clip-ellipse (o / e d center major minor normal norm ratio start end params spec
                           intervals run a b result copy ce cd nstart nend)
  (setq e (vlax-vla-object->ename o) d (entget e)
        center (cdr (assoc 10 d)) major (cdr (assoc 11 d))
        normal (cond ((cdr (assoc 210 d))) ('(0.0 0.0 1.0)))
        norm (distance '(0.0 0.0 0.0) normal) ratio (cdr (assoc 40 d)))
  (dc:stage "Clip ELLIPSE analytically" e)
  (if (<= norm 0.0) (dc:fail "ELLIPSE has an invalid normal."))
  (setq normal (mapcar '(lambda (x) (/ x norm)) normal)
        minor (mapcar '(lambda (x) (* x ratio)) (dc:cross normal major))
        center (trans center 0 1) major (trans major 0 1 T) minor (trans minor 0 1 T)
        start (cdr (assoc 41 d)) end (cdr (assoc 42 d)))
  (if (<= end start) (setq end (+ end (* 2.0 pi))))
  (cond
    ((or (> (abs (caddr major)) dc:eps) (> (abs (caddr minor)) dc:eps))
      (dc:issue "ELLIPSE (not parallel to UCS)") nil)
    (dc:contained (list o))
    (T
      (setq params (list start end))
      (foreach spec (list (list 0 dc:x0) (list 0 dc:x1) (list 1 dc:y0) (list 1 dc:y1))
        (setq params (append params
          (dc:ellipse-roots (nth (car spec) major) (nth (car spec) minor)
            (- (cadr spec) (nth (car spec) center)) start end))))
      (setq params (dc:unique params))
      (while (cdr params)
        (setq a (car params) b (cadr params))
        (if (dc:inside (dc:ellipse-point center major minor (/ (+ a b) 2.0)))
          (if run (setq run (list (car run) b)) (setq run (list a b)))
          (if run (setq intervals (cons run intervals) run nil)))
        (setq params (cdr params)))
      (if run (setq intervals (cons run intervals)))
      (foreach run (reverse intervals)
        (if (> (- (cadr run) (car run)) 1e-10)
          (progn
            (setq copy (dc:track (vla-Copy o)) ce (vlax-vla-object->ename copy) cd (entget ce)
                  nstart (rem (car run) (* 2.0 pi)) nend (rem (cadr run) (* 2.0 pi)))
            (if (equal nend 0.0 1e-12) (setq nend (* 2.0 pi)))
            (setq cd (subst (cons 41 nstart) (assoc 41 cd) cd)
                  cd (subst (cons 42 nend) (assoc 42 cd) cd))
            (if (null (entmod cd)) (dc:fail "Cannot set clipped ELLIPSE interval."))
            (setq result (cons copy result)))))
      (dc:del o) result)))
(defun dc:process (o depth / e d typ children child result block r tick)
  (setq e (vlax-vla-object->ename o) d (entget e) typ (cdr (assoc 0 d)))
  (dc:stage "Process copied entity" e)
  (cond
    ((= typ "HATCH") (dc:del o))
    ;; POINT location (DXF 10) is WCS, including exploded block children.
    ;; Keep the copy itself so its display properties and elevation survive.
    ((= typ "POINT")
      (if (dc:inside (trans (cdr (assoc 10 d)) 0 1))
        (setq result (list o))
        (dc:del o)))
    ((not (dc:overlap o)) (dc:del o))
    ((= typ "ELLIPSE")
      (setq tick (getvar "MILLISECS") result (dc:clip-ellipse o))
      (dc:time-add 'clip tick))
    ((= typ "SOLID")
      (setq tick (getvar "MILLISECS") result (dc:clip-solid o))
      (dc:time-add 'clip tick))
    ((= typ "LINE")
      (setq tick (getvar "MILLISECS") result (dc:clip-line o))
      (dc:time-add 'clip tick))
    ((member typ '("LWPOLYLINE" "POLYLINE" "ARC" "CIRCLE"))
      (if (or (and (= typ "POLYLINE") (/= 0 (logand (cdr (assoc 70 d)) 94)))
              (not (dc:planar o)) (and (assoc 39 d) (/= 0.0 (cdr (assoc 39 d)))))
        (dc:issue (strcat typ " (3D/fitted/thickness)"))
        (progn
          (setq tick (getvar "MILLISECS"))
          (setq result
            (if dc:contained
              (if (> (vlax-curve-getDistAtParam o (vlax-curve-getEndParam o)) dc:eps)
                (list o) (progn (dc:del o) nil))
              (dc:clip o)))
          (dc:time-add 'clip tick))))
    ((member typ '("TEXT" "MTEXT" "DIMENSION"))
      (if (= typ "DIMENSION")
        (command "_.DIMDISASSOCIATE" e ""))
      (setq result (list o)))
    ((= typ "INSERT")
      (setq block (vla-Item (vla-get-Blocks dc:doc) (vla-get-Name o)))
      (cond
        ((= :vlax-true (vla-get-IsXRef block)) (dc:issue "INSERT (XREF)"))
        ((> depth 32) (dc:issue "INSERT (nesting > 32)"))
        ((= :vlax-true (vla-get-HasAttributes o)) (dc:issue "INSERT (attributes: unsupported)"))
        (T
          (setq tick (getvar "MILLISECS"))
          (setq r (vl-catch-all-apply 'vla-Explode (list o)))
          (dc:time-add 'explode tick)
          (if (vl-catch-all-error-p r) (dc:issue "INSERT (cannot explode)")
            (progn
              (setq children (dc:array r))
              (foreach child children (dc:track child))
              (foreach child children
                (if (= "AcDbHatch" (vla-get-ObjectName child))
                  (dc:del child)
                  (progn
                    (dc:inherit child o)
                    (setq result (append result (dc:process child (1+ depth)))))))
              (dc:del o))))))
    (T (dc:issue typ)))
  result)
(defun dc:linetype (/ files dir f r)
  (if (not (tblsearch "LTYPE" "itten05"))
    (progn
      (setq files (list (findfile "acad.lin") (findfile "acadiso.lin") (findfile "itten05.lin")))
      (foreach dir (dc:split (strcat (getvar "DWGPREFIX") ";" (cond ((getenv "ACAD")) (""))) ";")
        (foreach f (vl-directory-files dir "*.lin" 1)
          (setq files (cons (strcat dir "/" f) files))))
      (foreach f files
        (if (and f (not (tblsearch "LTYPE" "itten05")))
          (vl-catch-all-apply 'vla-Load (list (vla-get-Linetypes dc:doc) "itten05" f))))))
  (if (not (tblsearch "LTYPE" "itten05"))
    (dc:fail "itten05 was not found in available LIN files.")))
(defun dc:split (s delim / p out)
  (while (setq p (vl-string-search delim s))
    (if (> p 0) (setq out (cons (substr s 1 p) out)))
    (setq s (substr s (+ p 2))))
  (if (/= s "") (setq out (cons s out))) (reverse out))
;; Options persist for this AutoCAD session. No drawing variables are changed.
(if (not (boundp '*dc-simple*)) (setq *dc-simple* nil))
(if (not (boundp '*dc-timing*)) (setq *dc-timing* nil))
(defun c:DETAILCUTOPTIONS (/ answer)
  (initget "Normal Simple")
  (setq answer (getkword "\nPlacement preview [Normal/Simple] <Normal>: "))
  (setq *dc-simple* (= answer "Simple"))
  (initget "On Off")
  (setq answer (getkword "\nTiming report [On/Off] <Off>: "))
  (setq *dc-timing* (= answer "On")) (princ))
(defun dc:time-add (key start / item elapsed)
  (setq elapsed (- (getvar "MILLISECS") start))
  (if (< elapsed 0) (setq elapsed (+ elapsed 4294967296.0)))
  (if (setq item (assoc key dc:times))
    (setq dc:times (subst (cons key (+ (cdr item) elapsed)) item dc:times))
    (setq dc:times (cons (cons key elapsed) dc:times))))
(defun dc:rect-vectors (a b / c d)
  (setq c (list (car a) (cadr b) (caddr a)) d (list (car b) (cadr a) (caddr a)))
  (list 7 a c 7 c b 7 b d 7 d a))
(defun dc:shift-vectors (vectors delta)
  (mapcar '(lambda (v) (if (listp v) (mapcar '+ v delta) v)) vectors))
;; Preview geometry is sampled once; final clipping never uses these samples.
;; Text, dimensions and blocks use their bounding boxes in the transient view.
(defun dc:preview-curve (o / a b n j p q out valid d)
  (setq d (entget (vlax-vla-object->ename o)))
  (if (= "LINE" (cdr (assoc 0 d)))
    ;; LINE endpoints are WCS DXF coordinates; no curve sampling is needed.
    (list 7 (trans (cdr (assoc 10 d)) 0 1) (trans (cdr (assoc 11 d)) 0 1))
    (progn
      (setq a (vlax-curve-getStartParam o) b (vlax-curve-getEndParam o))
      (if (and (numberp a) (numberp b))
        (progn
          (setq n (max 16 (min 512 (* 8 (1+ (fix (- b a))))))
                j 0 p (vlax-curve-getPointAtParam o a) valid (not (null p)))
          (while (and valid (< j n))
            (setq j (1+ j)
                  q (vlax-curve-getPointAtParam o
                      (if (= j n) b (+ a (* (- b a) (/ (float j) n))))))
            (if q
              (setq out (cons 7 (cons (trans p 0 1) (cons (trans q 0 1) out))) p q)
              (setq valid nil)))
          (if valid out))))))
(defun dc:preview-box (o / lo hi x y z pt xs ys elevation)
  (vla-GetBoundingBox o 'lo 'hi)
  (setq lo (vlax-safearray->list lo) hi (vlax-safearray->list hi))
  (foreach x (list (car lo) (car hi))
    (foreach y (list (cadr lo) (cadr hi))
      (foreach z (list (caddr lo) (caddr hi))
        (setq pt (trans (list x y z) 0 1)
              xs (cons (car pt) xs) ys (cons (cadr pt) ys) elevation (caddr pt)))))
  (dc:rect-vectors (list (apply 'min xs) (apply 'min ys) elevation)
                   (list (apply 'max xs) (apply 'max ys) elevation)))
(defun dc:preview-vectors (ss / i e o typ part vectors fallback omitted)
  (setq i 0 fallback 0 omitted 0)
  (repeat (sslength ss)
    (setq e (ssname ss i) i (1+ i) o (vlax-ename->vla-object e)
          typ (cdr (assoc 0 (entget e))))
    (dc:stage "Build placement preview" e)
    (setq part nil)
    (if (member typ '("LINE" "LWPOLYLINE" "POLYLINE" "CIRCLE" "ARC"))
      (progn
        (setq part (vl-catch-all-apply 'dc:preview-curve (list o)))
        (if (or (vl-catch-all-error-p part) (null part))
          (setq part nil fallback (1+ fallback)))))
    (if (null part)
      (setq part (vl-catch-all-apply 'dc:preview-box (list o))))
    (if (vl-catch-all-error-p part)
      (setq omitted (1+ omitted))
      (setq vectors (append part vectors))))
  (if (> fallback 0)
    (princ (strcat "\nPreview: " (itoa fallback) " curves shown as bounding boxes.")))
  (if (> omitted 0)
    (princ (strcat "\nPreview: " (itoa omitted) " objects could not be displayed; selection is retained.")))
  vectors)
(defun dc:pick-rectangle (base / event pos done)
  (princ "\nUpper-left corner (click; Esc cancels): ")
  (while (not done)
    (setq event (grread T 15 0))
    (cond
      ((member (car event) '(3 5))
        (setq pos (list (car (cadr event)) (cadr (cadr event)) (caddr base)))
        (redraw) (grvecs (dc:rect-vectors base pos))
        (if (= (car event) 3) (setq done T)))
      ((and (= (car event) 2) (= (cadr event) 27)) (dc:fail "Cancelled."))))
  pos)
(defun dc:unhighlight (ss / i e)
  (if ss
    (progn
      (setq i 0)
      (repeat (sslength ss)
        (setq e (ssname ss i) i (1+ i))
        (if (entget e) (redraw e 4))))))
(defun dc:pick-placement (base source vectors ss / marker preview objects o raw a b pos tick i)
  ;; Use AutoCAD's native drag/point input. Only disposable preview entities move.
  ;; The actual selected objects are copied and clipped after this returns.
  (dc:stage "Native placement preview" nil)
  (setq tick (getvar "MILLISECS") preview (ssadd))
  (setq marker (dc:poly
    (list (list base 0.0 0.0 0.0)
          (list (list dc:x0 dc:y0 (caddr base)) 0.0 0.0 0.0)
          (list (list dc:x0 dc:y1 (caddr base)) 0.0 0.0 0.0)
          (list (list dc:x1 dc:y1 (caddr base)) 0.0 0.0 0.0)) T
    (list (cons 8 (getvar "CLAYER")) '(62 . 7) '(6 . "Continuous") '(370 . 0))))
  (setq objects (list marker))
  (ssadd (vlax-vla-object->ename marker) preview)
  (if (not *dc-simple*)
    (progn
      (setq raw vectors)
      (while raw
        (setq a (cadr raw) b (caddr raw) raw (cdddr raw))
        (if (> (distance a b) dc:eps)
          (progn
            (setq o (dc:track (vla-AddLine dc:space
                      (vlax-3d-point (trans a 1 0)) (vlax-3d-point (trans b 1 0))))
                  objects (cons o objects))
            (ssadd (vlax-vla-object->ename o) preview))))))
  ;; Remove grips before entering MOVE; keep a plain highlight on sources.
  (sssetfirst nil nil)
  (setq i 0)
  (repeat (sslength ss) (redraw (ssname ss i) 3) (setq i (1+ i)))
  (grvecs source)
  (setvar "DRAGMODE" 2)
  (dc:time-add 'display tick)
  (princ "\nPlacement point: click or enter coordinates in the native MOVE prompt; Esc cancels.")
  (command "_.MOVE" preview "" "_non" base pause)
  (if (> (getvar "CMDACTIVE") 0) (dc:fail "Placement input did not finish."))
  (setq tick (getvar "MILLISECS"))
  (setq o (vlax-vla-object->ename marker)
        pos (trans (append (cdr (assoc 10 (entget o)))
                           (list (cdr (assoc 38 (entget o))))) o 1))
  (foreach o objects (dc:del o))
  (setvar "DRAGMODE" olddrag)
  (dc:time-add 'display tick)
  pos)
(defun dc:end-undo (/ r)
  ;; End closes the group; it does not undo any drawing edits.
  ;; Use the same command API for Begin/End, including error recovery.
  (if (/= 0 (logand 8 (getvar "UNDOCTL")))
    (setq r (vl-catch-all-apply 'command-s (list "_.UNDO" "_End"))))
  (and (not (vl-catch-all-error-p r)) (= 0 (logand 8 (getvar "UNDOCTL")))))
(defun c:DETAILCUT (/ *error* dc:doc dc:space dc:made dc:issues dc:reason dc:eps
                       dc:step dc:entity-info dc:contained dc:times candidates candidate e tick destination vectors source
                       dc:x0 dc:x1 dc:y0 dc:y1 undo oldecho olddrag p1 p2 z ss i o copy
                       selected outputs frame props corners moveSS layer success pair rollback)
  (setq dc:doc (vla-get-ActiveDocument (vlax-get-acad-object))
        dc:space (if (= 1 (getvar "CVPORT")) (vla-get-PaperSpace dc:doc) (vla-get-ModelSpace dc:doc))
        dc:eps 1e-7 oldecho (getvar "CMDECHO") olddrag (getvar "DRAGMODE"))
  (defun *error* (msg)
    (vl-catch-all-apply 'dc:cleanup nil)
    (if undo
      (progn
        (setq undo nil)
        ;; Never run U while our group is still open.
        (if (dc:end-undo)
          (progn
            (setq rollback (vl-catch-all-apply 'command-s (list "_.U")))
            (if (vl-catch-all-error-p rollback)
              (princ "\nDETAILCUT: Automatic undo failed; inspect the drawing.")))
          (princ "\nDETAILCUT: Cannot close UNDO group. Run UNDO End."))))
    ;; Display cleanup must not prevent the UNDO group from being closed.
    (vl-catch-all-apply 'sssetfirst (list nil nil))
    (vl-catch-all-apply 'dc:unhighlight (list selected))
    (vl-catch-all-apply 'redraw nil)
    (vl-catch-all-apply 'setvar (list "CMDECHO" oldecho))
    (vl-catch-all-apply 'setvar (list "DRAGMODE" olddrag))
    (if dc:reason (princ (strcat "\nDETAILCUT: " dc:reason))
      (if msg (princ (strcat "\nDETAILCUT: " msg))))
    (if dc:step (princ (strcat "\nStage: " dc:step dc:entity-info)))
    (princ))
  (if (= 0 (logand 1 (getvar "UNDOCTL"))) (dc:fail "Enable UNDO before DETAILCUT."))
  (if (/= 0 (logand 8 (getvar "UNDOCTL")))
    (if (dc:end-undo)
      (princ "\nDETAILCUT: Closed the previous UNDO group.")
      (dc:fail "Cannot close the previous UNDO group. Run UNDO End.")))
  (setq p1 (getpoint "\nDETAILCUT - lower-right corner: "))
  (if (null p1) (dc:fail "Cancelled."))
  (while (null p2)
    (setq p2 (dc:pick-rectangle p1))
    (if (null p2) (dc:fail "Cancelled."))
    (if (or (>= (car p2) (- (car p1) dc:eps)) (<= (cadr p2) (+ (cadr p1) dc:eps)))
      (progn (princ "\nChoose an upper-left point with nonzero width and height.") (setq p2 nil))))
  (setq dc:x0 (car p2) dc:x1 (car p1) dc:y0 (cadr p1) dc:y1 (cadr p2) z (caddr p1))
  (setq layer (tblsearch "LAYER" "USR2"))
  (if (and layer (or (< (cdr (assoc 62 layer)) 0) (/= 0 (logand 5 (cdr (assoc 70 layer))))))
    (dc:fail "USR2 is off, frozen or locked. Adjust it explicitly before running."))
  ;; Snapshot live top-level entities. ActiveX space enumeration can expose
  ;; erased database objects; do not call GetBoundingBox on those wrappers.
  (dc:stage "Collect live entities in current space" nil)
  (setq tick (getvar "MILLISECS"))
  (setq selected (ssadd))
  (setq candidates (ssget "_X"
    (list (cons 410 (if (= 1 (getvar "CVPORT")) (getvar "CTAB") "Model"))
          '(-4 . "<NOT") '(0 . "HATCH") '(-4 . "NOT>"))))
  (setq candidate 0)
  (if candidates
    (repeat (sslength candidates)
      (setq e (ssname candidates candidate) candidate (1+ candidate))
      (if (entget e)
        (progn
          (dc:stage "Read candidate bounding box" e)
          (setq o (vlax-ename->vla-object e))
          (if (dc:overlap o) (ssadd e selected))))))
  (if (= 0 (sslength selected)) (dc:fail "No copy candidates in the rectangle."))
  (dc:time-add 'acquire tick)
  (setq tick (getvar "MILLISECS"))
  (sssetfirst nil selected)
  (setq source (dc:rect-vectors p1 p2))
  (grvecs source)
  (if (not *dc-simple*) (setq vectors (dc:preview-vectors selected)))
  (dc:time-add 'display tick)
  (command-s "_.UNDO" "_Begin") (setq undo T)
  (setq destination (dc:pick-placement p1 source vectors selected))
  (setvar "CMDECHO" 0)
  (dc:stage "Load itten05" nil)
  (dc:linetype)
  (if (null layer) (vla-Add (vla-get-Layers dc:doc) "USR2"))
  (setq i 0)
  (repeat (sslength selected)
    (setq e (ssname selected i))
    (dc:stage "Copy source entity" e)
    (setq o (vlax-ename->vla-object e) i (1+ i)
          copy (dc:track (vla-Copy o)))
    (setq outputs (append outputs (dc:process copy 0))))
  (if dc:issues
    (progn (dc:stage "Validate supported object types" nil)
           (foreach pair dc:issues (princ (strcat "\nUnsupported: " (car pair) " x " (itoa (cdr pair)))))
           (dc:fail "Unsupported objects detected; all generated objects rolled back.")))
  (if (null outputs) (dc:fail "No supported geometry remains inside the rectangle."))
  (dc:stage "Move completed copies" nil)
  (foreach o outputs
    (vla-Move o (vlax-3d-point (trans p1 1 0)) (vlax-3d-point (trans destination 1 0))))
  ;; Only after all copies have been processed and moved, create the source mark.
  (dc:stage "Create source frame and cross" nil)
  (setq props '((8 . "USR2") (6 . "itten05") (62 . 256) (370 . -1) (48 . 1.0))
        corners (list (list dc:x0 dc:y0 z) (list dc:x1 dc:y0 z)
                      (list dc:x1 dc:y1 z) (list dc:x0 dc:y1 z)))
  (setq frame (list (dc:poly (mapcar '(lambda (p) (list p 0.0 0.0 0.0)) corners) T props)
                   (dc:poly (list (list (nth 0 corners) 0.0 0.0 0.0) (list (nth 2 corners) 0.0 0.0 0.0)) nil props)
                   (dc:poly (list (list (nth 1 corners) 0.0 0.0 0.0) (list (nth 3 corners) 0.0 0.0 0.0)) nil props)))
  (setq tick (getvar "MILLISECS"))
  (setq ss (ssadd)) (foreach o frame (ssadd (vlax-vla-object->ename o) ss))
  (command "_.DRAWORDER" ss "" "_Front")
  (sssetfirst nil nil) (dc:unhighlight selected) (redraw)
  (dc:time-add 'display tick)
  (setvar "CMDECHO" oldecho) (setvar "DRAGMODE" olddrag)
  (if (not (dc:end-undo)) (dc:fail "Cannot close DETAILCUT UNDO group."))
  (setq undo nil dc:made nil)
  (if *dc-timing*
    (foreach pair '(acquire explode clip display)
      (princ (strcat "\nTiming " (vl-symbol-name pair) ": "
        (rtos (/ (cond ((cdr (assoc pair dc:times))) (0.0)) 1000.0) 2 3) " s"))))
  (princ (strcat "\nDETAILCUT complete: " (itoa (length outputs)) " objects + source frame/cross. Undo once to restore."))
  (princ))
(princ "\nDETAILCUT loaded (2026-09-22 rev10). Command: DETAILCUT")
(princ)
