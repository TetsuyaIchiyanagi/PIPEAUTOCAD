;; KIKISET/KIKITABLE、KIKITABLE_tests.lsp、KANKI_tests.lsp の後にロード。
(defun kht:record ()
  '(("SYSTEM" . "HEX") ("NUM" . "1") ("EQUIP_TYPE" . "全熱交換器")
    ("MAKER" . "三菱電機") ("MODEL" . "VL-200ZSD3") ("TYPE" . "天井埋込形")
    ("DUCT_DIA" . "100") ("AIRFLOW" . "48") ("STATIC_PRESSURE" . "20")
    ("TEMP_EX_EFF" . "76") ("ENTHALPY_HEAT_EFF" . "63") ("ENTHALPY_COOL_EFF" . "58")
    ("PHASE" . "1") ("VOLT" . "100") ("POWER" . "0.059") ("LOCATION" . "廊下") ("FLOOR" . "1")))
(defun c:KANKIHEXTEST (/ kt:config kt:tags kt:plan kt:warnings ks:category-id ktt:passed data specs layout entry)
  (setq kt:config (append kt:vent-config kt:aircon-config) kt:tags kt:vent-tags
        ks:category-id "KANKI" ktt:passed 0 data (kht:record) specs (kt:vent-spec data))
  (ktt:assert (equal specs '("天井埋込形" "能力 100φ × 48m3/h × 20Pa 温度交換効率 76%" "その他付属品一式")) "HEX three lines")
  (ktt:assert (= (cadr (kt:vent-spec (vl-remove (assoc "STATIC_PRESSURE" data) data))) "能力 100φ × 48m3/h 温度交換効率 76%") "Missing pressure")
  (ktt:assert (= (cadr (kt:vent-spec (vl-remove (assoc "TEMP_EX_EFF" data) data))) "能力 100φ × 48m3/h × 20Pa") "Missing efficiency")
  (ktt:assert (= (caddr (kt:vent-spec (cons '("ACCESSORY" . "天井パネル、リモコン") data))) "天井パネル、リモコン") "Explicit accessory")
  (ktt:assert (equal (kt:vent-spec '(("EQUIP_TYPE" . "全熱交換器"))) '("" "" "その他付属品一式")) "Empty fields do not produce units")
  (foreach entry '(("TEMP_EX_EFF" . "76") ("ENTHALPY_HEAT_EFF" . "63") ("ENTHALPY_COOL_EFF" . "58"))
    (ktt:assert (equal (assoc (car entry) (ks:record-data (cons 3 data))) entry) (car entry)))
  (ktt:assert (assoc "ACCESSORY" (ks:record-data '(3 ("ACCESSORY" . "リモコン")))) "Accessory mapping")
  (setq layout (kt:plan-vent (kt:group (list data)) '(("1" . 10)) 11 12))
  (ktt:assert (equal (car layout) '((6 3))) "Three rows plus gap")
  (foreach entry '(((6 2) . "HEX-1") ((6 3) . "全熱交換器") ((6 4) . "三菱電機")
                  ((7 4) . "VL-200ZSD3") ((6 6) . "廊下") ((6 7) . "1") ((6 8) . "100")
                  ((6 10) . 1) ((6 11) . 1) ((8 5) . "その他付属品一式"))
    (ktt:assert (equal (ktt:planned (caar entry) (cadar entry)) (cdr entry)) (vl-princ-to-string (car entry))))
  (ktt:assert (equal (ktt:planned 6 9) 0.059 1e-10) "HEX power")
  (setq layout (kt:plan-vent (kt:group (list (kvt:record "A" "1") data)) '(("1" . 10)) 11 12))
  (ktt:assert (equal (car layout) '((6 2) (9 3))) "Mixed EF unchanged and HEX expanded")
  (ktt:assert (= (ktt:planned 10 4) "VL-200ZSD3") "Mixed model row")
  (princ (strcat "\nKANKIHEXTEST PASSED: " (itoa ktt:passed))) (princ))
(defun kht:book-test (path / *error* kt:objects kt:excel kt:book kt:reason kt:stage kt:cell-context kt:log-path
                           kt:config kt:tags kt:raw-tags kt:plan kt:warnings ktt:passed records sheets ws)
  (defun *error* (msg) (princ (strcat "\nHEX BOOK FAILED: " (if kt:reason kt:reason msg))) (kt:cleanup) (princ))
  (setq kt:config (append kt:vent-config kt:aircon-config) kt:tags kt:vent-tags
        kt:raw-tags (kt:raw-columns) ktt:passed 0 records (list (kht:record)))
  (kt:open path) (kt:write-book records (kt:group records))
  (setq sheets (kt:own (vlax-get-property kt:book 'Worksheets)) ws (kt:sheet sheets "機器表 (換気設備)"))
  (ktt:assert (= (kt:cell-value ws 6 2) "HEX-1") "Excel symbol")
  (ktt:assert (= (kt:cell-value ws 7 4) "VL-200ZSD3") "Excel model")
  (ktt:assert (= (kt:cell-value ws 7 5) "能力 100φ × 48m3/h × 20Pa 温度交換効率 76%") "Excel efficiency")
  (ktt:assert (= (kt:cell-value ws 8 5) "その他付属品一式") "Excel accessories")
  (ktt:assert (null (kt:cell-value ws 9 5)) "Excel gap")
  (ktt:assert (= (kt:cell-value ws 39 2) "a") "Lower table preserved")
  (vlax-invoke-method kt:book 'Save) (kt:cleanup)
  (princ (strcat "\nHEX BOOK PASSED: " (itoa ktt:passed))) (princ))
