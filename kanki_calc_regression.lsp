;; Isolated blank DWG + disposable local workbook only.
(setq kr:count 0)
(defun *error* (msg) (princ (strcat "\nREGRESSION_ERROR: " msg)) (kt:cleanup) (princ))
(defun kr:blank (v) (or (null v) (equal v "")))
(defun kr:assert (condition label)
  (if (not condition) (progn (princ (strcat "\nFAIL: " label)) (kt:cleanup) (exit)))
  (setq kr:count (1+ kr:count)) (princ (strcat "\nPASS: " label)))
(defun kr:record (floor room area height airflow handle)
  (list '("SYSTEM" . "EF") '("NUM" . "3") '("MODEL" . "TEST-430") '("EQUIP_TYPE" . "ダクト用換気扇")
    '("TYPE" . "低騒音形") '("STATIC_PRESSURE" . "80") '("PHASE" . "1") '("VOLT" . "100") '("POWER" . "0.018")
    (cons "FLOOR" floor) (cons "LOCATION" room) (cons "FLOOR_AREA" area)
    (cons "CEILING_HEIGHT" height) (cons "AIRFLOW" airflow) (cons "HANDLE" handle)))
(setq kr:a (kr:record "01" " 事務室 " "43.7" "2.4" "430" "A1")
      kr:b (kr:record "1" "事務室" "43.70" "2.40" "430" "A2")
      kr:c (kr:record "2" "事務室" "10" "3" "100" "A3"))
(kr:assert (= (length (kc:rooms (list kr:a kr:b kr:c))) 2) "room-key-floor-and-trim")
(kr:assert (= (length (kc:rooms (list kr:a (kr:record "1" "事 務室" "10" "3" "100" "A4")))) 2) "internal-space-preserved")
(kr:assert (equal (car (kc:dimension (list kr:a kr:b) "FLOOR_AREA")) 43.7 1e-9) "area-not-summed")
(kr:assert (equal (* (car (kc:dimension (list kr:a kr:b) "FLOOR_AREA")) 2.4) 104.88 1e-9) "volume-104.88")
(foreach kr:v '("" "0" "-1" "bad" "43m2" "1+2") (kr:assert (null (kc:positive kr:v)) (strcat "invalid-positive-" kr:v)))
(kr:assert (equal (car (kc:dimension (list kr:a (kr:record "1" "事務室" "" "2.4" "430" "A4")) "FLOOR_AREA")) 43.7 1e-9) "partial-missing-adopts-valid")
(kr:assert (= (car (kc:dimension (list kr:a kr:c) "FLOOR_AREA")) "") "area-conflict-blank")
(setq kr:uses '((("EF" "3" "TEST-430") "排気" "単室")))
(kr:assert (= (car (kc:capacity (list kr:a kr:b) kr:uses)) 860.0) "airflow-two-times-430")
(kr:assert (= (nth 2 (kc:capacity (list kr:a kr:b) kr:uses)) "EF-3×2台") "equipment-count-text")
(kr:assert (= (cadr (kc:capacity (list kr:a kr:b) kr:uses)) 80.0) "static-not-summed")
(kr:assert (= (car (kc:capacity (list kr:a kr:b) nil)) "") "no-symbol-inference")
(kr:assert (= (car (kc:capacity (list (subst '("EQUIP_TYPE" . "全熱交換器") (assoc "EQUIP_TYPE" kr:a) kr:a)) kr:uses)) "") "heat-exchanger-excluded")
(kr:assert (= (car (kc:capacity (list kr:a (subst '("STATIC_PRESSURE" . "90") (assoc "STATIC_PRESSURE" kr:b) kr:b)) kr:uses)) "") "pressure-conflict-excluded")
(kr:assert (= (kc:excel-floor "２F") "2") "legacy-excel-fullwidth-floor")
(kr:assert (null (kt:floor "２")) "cad-floor-unchanged")
(setq kt:tags kt:vent-tags)
(kr:assert (not (member "FLOOR_AREA" (mapcar 'car (kt:consensus "EF-3" (list kr:a kr:c))))) "room-dimensions-excluded-equipment-consensus")
(kr:assert (not (ks:writable-p "FLOOR_AREA" "12")) "kikiset-area-protected")
(kr:assert (not (ks:writable-p "CEILING_HEIGHT" "3")) "kikiset-height-protected")
(kr:assert (kc:chart-gap-formula "=IF($T28=\"\",NA(),$T28)") "intentional-chart-na-recognized")
(kr:assert (not (kc:chart-gap-formula "=IF(T28=\"\",NA(),1)")) "other-na-formula-not-exempted")

;; Open only the disposable fixture; exercise the actual three-sheet transaction.
(setenv "PIPEAUTOCAD_KANKI_TEMPLATE" (strcat (vl-filename-directory kr:fixture) "/code/換気計算テンプレート.xlsx"))
(setq kt:config (append kt:vent-config kt:aircon-config) kt:raw-tags (kt:raw-columns))
(kt:open kr:fixture)
(setq kr:sheets (kt:own (vlax-get-property kt:book 'Worksheets)))
(setq kr:ws (kt:sheet kr:sheets kc:sheet-name))
;; Fixture-only repair/removal: original's broken inputs are never changed.
(vlax-invoke-method kr:ws 'Delete)
(setq kr:ws nil)
(kt:write-book (list kr:a kr:b) (kt:group (list kr:a kr:b)))
(setq kr:ws kc:verify-sheet kr:cfg (kt:sheet kr:sheets kc:settings-name) kr:eq (kt:sheet kr:sheets kc:equipment-name))
(kr:assert (equal (kt:cell-value kr:ws 6 7) 104.88 1e-9) "excel-volume")
(kr:assert (= (kt:cell-value kr:ws 6 20) "要確認") "unconfigured-equipment-never-circle")
(kr:assert (kr:blank (kt:cell-value kr:ws 6 16)) "unset-demand-blank")
(kr:assert (= (kt:cell-value (kt:sheet kr:sheets "CAD_DATA") 1 1) "SYSTEM") "aircon-raw-preserved")
(kt:put-matrix kr:eq 2 1 '(("EF" "3" "TEST-430" "排気" "単室")))
(kt:put-matrix kr:cfg 2 3 '(("対象外" "適用" "適用" "単室" 10 "四捨五入")))
(kt:put kr:ws 6 8 6) (kt:put kr:ws 6 9 7.5) (kt:put kr:ws 6 10 20)
(kt:put kr:ws 6 12 0.5) (kt:put kr:ws 6 14 3) (kt:put kr:ws 6 17 3)
(kt:write-book (list kr:a kr:b) (kt:group (list kr:a kr:b)))
(setq kr:ws kc:verify-sheet)
(kr:assert (= (kt:cell-value kr:ws 6 18) 860.0) "excel-airflow-860")
(kr:assert (= (kt:cell-value kr:ws 6 15) 310.0) "round-nearest-10")
(kr:assert (= (kt:cell-value kr:ws 6 16) 310.0) "demand-max-applicable")
(kr:assert (= (kt:cell-value kr:ws 6 20) "○") "configured-capacity-circle")
(kr:assert (= (kt:cell-value kr:ws 6 8) 6.0) "manual-persons-preserved")
(foreach kr:p '((9 . 7.5) (10 . 20.0) (12 . 0.5) (14 . 3.0) (17 . 3.0))
  (kr:assert (= (kt:cell-value kr:ws 6 (car kr:p)) (cdr kr:p)) (strcat "manual-preserved-col-" (itoa (car kr:p)))))
(kt:put-matrix kr:cfg 2 3 '(("適用" "対象外" "対象外" "単室" 10 "四捨五入")))
(kt:put kr:ws 6 8 100)
(vlax-invoke-method kt:excel 'CalculateFull) (kc:verify)
(kr:assert (= (kt:cell-value kr:ws 6 20) "×") "insufficient-capacity-cross")
(kt:put kr:cfg 2 3 "未設定")
(vlax-invoke-method kt:excel 'CalculateFull) (kc:verify)
(kr:assert (= (kt:cell-value kr:ws 6 20) "要設定") "unset-method-gates-decision")
(kt:put-matrix kr:cfg 2 3 '(("対象外" "適用" "適用" "単室" 10 "切り上げ")))
(vlax-invoke-method kt:excel 'CalculateFull)
(kr:assert (= (kt:cell-value kr:ws 6 15) 320.0) "round-up-10")
(kt:put kr:cfg 2 7 25)
(vlax-invoke-method kt:excel 'CalculateFull)
(kr:assert (= (kt:cell-value kr:ws 6 15) 325.0) "round-unit-editable")
(kt:put kr:cfg 2 7 10)
;; Add room sorting before original, change CAD area, keep manual inputs by key.
(setq kr:changed (subst '("FLOOR_AREA" . "50") (assoc "FLOOR_AREA" kr:a) kr:a)
      kr:new (kr:record "0" "新室" "10" "3" "430" "A4"))
(kt:write-book (list kr:new kr:changed) (kt:group (list kr:new kr:changed)))
(setq kr:ws kc:verify-sheet)
(kr:assert (= (kt:cell-value kr:ws 7 4) "事務室") "room-sort-numeric-floor")
(kr:assert (= (kt:cell-value kr:ws 7 8) 100.0) "input-follows-room-after-insert")
(kr:assert (= (kt:cell-value kr:ws 7 5) 50.0) "cad-area-updated")
(kr:assert (= (kt:cell-value kr:ws 7 7) 120.0) "volume-not-stale")
(kr:assert (= (kt:cell-value kr:ws 6 20) "要設定") "new-room-conditions-unset")
;; Conflict dependencies and missing/invalid airflow.
(kt:write-book (list kr:a kr:changed) (kt:group (list kr:a kr:changed)))
(setq kr:ws kc:verify-sheet)
(kr:assert (kr:blank (kt:cell-value kr:ws 6 5)) "conflict-area-empty")
(kr:assert (kr:blank (kt:cell-value kr:ws 6 7)) "conflict-volume-empty")
(kr:assert (= (kt:cell-value kr:ws 6 20) "要確認") "conflict-never-circle")
(kr:assert (not (null (kt:sheet kr:sheets kc:archive-name))) "removed-room-archived")
;; Boundary and reference preservation, including independent right formulas.
(kt:put kr:ws 26 3 "BOTTOM-KEEP") (kt:put kr:ws 6 1 "LEFT-KEEP")
(setq kr:cell (kt:range kr:ws 26 23 26 23)) (vlax-put-property kr:cell 'Formula "=SUM(1,2)") (kt:drop kr:cell)
(setq kr:many nil kr:i 1)
(repeat 30
  (setq kr:many (cons (kr:record "1" (strcat "室" (itoa kr:i)) "10" "3" "430" (itoa kr:i)) kr:many) kr:i (1+ kr:i)))
(kt:write-book kr:many (kt:group kr:many))
(setq kr:ws kc:verify-sheet)
(kr:assert (= (kc:end kr:ws) 35) "detail-expansion-print-area")
(kr:assert (= (kt:cell-value kr:ws 15 4) "室10") "room-natural-sort")
(kr:assert (= (kt:cell-value kr:ws 36 3) "BOTTOM-KEEP") "bottom-moves-with-insertion")
(kr:assert (= (kt:cell-value kr:ws 36 23) 3.0) "right-formula-preserved")
(kr:assert (= (kt:cell-value kr:ws 6 1) "LEFT-KEEP") "left-data-preserved")
(kt:write-book (list kr:a) (kt:group (list kr:a)))
(setq kr:ws kc:verify-sheet)
(kr:assert (kr:blank (kt:cell-value kr:ws 7 4)) "shrink-clears-stale-rooms")
(kr:assert (= (kt:cell-value kr:ws 36 3) "BOTTOM-KEEP") "shrink-preserves-bottom")
(vlax-invoke-method kt:book 'Save)
(kr:assert (= (kt:unwrap (vlax-get-property kt:book 'Saved)) :vlax-true) "save-completed")
(kt:cleanup)
(kt:open kr:fixture)
(setq kr:sheets (kt:own (vlax-get-property kt:book 'Worksheets)) kr:ws (kt:sheet kr:sheets kc:sheet-name))
(kr:assert (= (kt:cell-value kr:ws 6 4) "事務室") "saved-reopen-room")
(kr:assert (= (kt:cell-value kr:ws 36 23) 3.0) "saved-reopen-right-formula")
(kt:cleanup)
(kr:assert (null kt:excel) "owned-excel-released")
(princ (strcat "\nKANKI_REGRESSION_PASS=" (itoa kr:count)))
(princ)
