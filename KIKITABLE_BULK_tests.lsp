;; KIKITABLE.lsp / KIKITABLE_tests.lsp / KIKITABLE_COM_tests.lsp を先にロード。
;; KIKITABLEBULKTEST：専用の一時Excelのみ使用。実図面・案件Excelは変更しない。
(defun c:KIKITABLEBULKTEST (/ *error* kt:objects kt:excel kt:book kt:reason kt:stage
    kt:config kt:tags kt:raw-tags kt:plan kt:warnings kt:log-path kt:cell-context
    ktt:passed ws sheets raw area records record i calculation result)
  (defun *error* (msg)
    (princ (strcat "\nKIKITABLEBULKTEST FAILED: " (if kt:reason kt:reason msg)))
    (kt:cleanup) (princ))
  (setq kt:config kt:aircon-config kt:tags kt:aircon-tags
        kt:raw-tags (append (kt:raw-columns) '("NOTE" "MISSING")) ktt:passed 0)
  (setq ws (ktt:fixture) area (kt:range ws 6 2 12 13))
  (vlax-invoke-method area 'UnMerge) (kt:drop area)
  (setq record (ktt:record "PAC-01" "=literal" "1" "=1+1")
        records (list record) calculation (kt:unwrap (vlax-get-property kt:excel 'Calculation)))
  (kt:write-book records (kt:group records))
  (ktt:assert (= (kt:unwrap (vlax-get-property kt:excel 'Calculation)) calculation) "Calculation mode restored")
  (ktt:assert (= (kt:cell-value ws 6 2) "PAC-01") "Bulk identifier retains leading zero")
  (ktt:assert (= (kt:cell-value ws 6 6) "=literal") "Bulk location is literal")
  (ktt:assert (= (kt:cell-value ws 6 13) "=1+1") "Bulk note is literal")
  (ktt:assert (= (kt:cell-value ws 6 12) 1) "Quantity stays numeric")
  (ktt:assert (equal (kt:cell-value ws 6 9) 2.22 1e-10) "Power stays numeric")
  (ktt:assert (null (kt:cell-value ws 7 2)) "Sparse cells remain blank")
  (setq area (kt:range ws 6 13 6 13))
  (ktt:assert (equal (kt:unwrap (vlax-get-property area 'HasFormula)) :vlax-false) "No injected formula")
  (kt:drop area)
  (setq sheets (kt:own (vlax-get-property kt:book 'Worksheets)) raw (kt:sheet sheets "CAD_DATA"))
  (ktt:assert (= (kt:cell-value raw 2 2) "01") "Raw number stays text")
  (ktt:assert (null (kt:cell-value raw 2 (1+ (vl-position "MISSING" kt:raw-tags)))) "Missing raw value stays blank")
  ;; 500行の境界をまたぐデータ。見出し・各個体の順序・末尾を検査。
  (setq records nil i 0)
  (repeat 1001
    (setq i (1+ i) records (cons (ktt:record "PAC-01" (itoa i) "1" "") records)))
  (kt:write-raw raw (reverse records))
  (ktt:assert (= (kt:cell-value raw 1 1) "SYSTEM") "Chunk header")
  (foreach i '(2 500 501 1000 1001 1002)
    (ktt:assert (= (kt:cell-value raw i (1+ (vl-position "LOCATION" kt:raw-tags))) (itoa (1- i)))
      (strcat "Chunk record row " (itoa i))))
  (kt:write-raw raw (list record))
  (ktt:assert (null (kt:cell-value raw 501 1)) "Rerun removes later chunks")
  ;; 結合が混在する帳票も旧検査へ進み、枠外への結合を拒否する。
  (setq area (kt:range ws 6 2 13 2))
  (vlax-invoke-method area 'Merge :vlax-false) (kt:drop area)
  (setq kt:reason nil result (vl-catch-all-apply 'kt:check-boundary (list ws 19 13)))
  (ktt:assert (and (vl-catch-all-error-p result) kt:reason) "Cross-frame merge rejected")
  (setq kt:reason nil)
  (kt:cleanup)
  (ktt:assert (and (null kt:excel) (null kt:book) (null kt:objects)) "Owned COM objects cleaned")
  (kt:cleanup)
  (princ (strcat "\nKIKITABLEBULKTEST PASSED: " (itoa ktt:passed))) (princ))
