;; GARARITABLE / Windows AutoCAD 2021+ / Excel / UTF-8, LISPSYS=1 or 2
(vl-load-com)
(setq garari:version "2026-10-30.5")
(setq garari:directory
  (cond
    ((and (boundp '*load-truename*) *load-truename*) (vl-filename-directory *load-truename*))
    ((and (boundp '*load-pathname*) *load-pathname*) (vl-filename-directory *load-pathname*))
    ((findfile "08_garari_table.lsp") (vl-filename-directory (findfile "08_garari_table.lsp")))
    ((and (boundp 'pa-path) pa-path (findfile (strcat pa-path "08_garari_table.lsp"))) pa-path)))
(setq garari:config '((fd-temp . "72") (mesh-spec . "10") (sound . "なし")
  (order . natural) (widths 8 28 28 48) (floor-width . 7) (note-width . 24)
  (page-height . 680) (show-result . T) (table-sheet . "機器表（ガラリ）")))
(setq garari:tags '("GARARI" "DIA" "FD" "SHAPE" "MATERIAL" "MESH" "ROOM" "FLOOR" "SOUND"))
(setq garari:keys '("SHAPE" "DIA" "FD" "MATERIAL" "MESH" "MESH_SPEC" "FD_TEMP" "SOUND"))
(defun garari:get (a k) (if (assoc k a) (cdr (assoc k a)) ""))
(defun garari:set (a k v) (if (assoc k a) (subst (cons k v) (assoc k a) a) (cons (cons k v) a)))
(defun garari:trim (s) (vl-string-trim " \t\r\n　" (if s s "")))
(defun garari:half (s) (vl-string-translate
  "０１２３４５６７８９ＡＢＣＤＥＦＧＨＩＪＫＬＭＮＯＰＱＲＳＴＵＶＷＸＹＺａｂｃｄｅｆｇｈｉｊｋｌｍｎｏｐｑｒｓｔｕｖｗｘｙｚ"
  "0123456789ABCDEFGHIJKLMNOPQRSTUVWXYZabcdefghijklmnopqrstuvwxyz" (garari:trim s)))
(defun garari:digits (s / ok c) (setq ok (/= s ""))
  (foreach c (vl-string->list s) (if (or (< c 48) (> c 57)) (setq ok nil))) ok)
(defun garari:dia (s / x)
  (setq x (strcase (garari:half s)))
  (if (member (substr x 1 1) '("φ" "Φ")) (setq x (substr x 2)))
  (cond ((and (>= (strlen x) 2) (= (substr x (1- (strlen x))) "MM")) (setq x (substr x 1 (- (strlen x) 2))))
        ((and (> (strlen x) 0) (member (substr x (strlen x)) '("φ" "Φ"))) (setq x (substr x 1 (1- (strlen x))))))
  (if (and (garari:digits x) (> (atoi x) 0) (< (strlen x) 9)) (itoa (atoi x)) ""))
(defun garari:bool (s / x) (setq x (strcase (garari:half s)))
  (cond ((member x '("あり" "有" "有り" "YES" "Y" "1")) "あり")
        ((member x '("なし" "無" "無し" "NO" "N" "0")) "なし") (T "")))
(defun garari:normalize (raw cfg / out tag s)
  (foreach tag garari:tags
    (setq s (garari:trim (garari:get raw tag)))
    (setq s (cond ((= tag "DIA") (garari:dia s))
      ((member tag '("FD" "MESH")) (garari:bool s))
      ((= tag "SOUND") (if (assoc tag raw) (garari:bool s) (cdr (assoc 'sound cfg))))
      ((= tag "SHAPE") (cond ((member s '("深形" "深型")) "深型") ((member s '("平形" "平型")) "平型") (T "")))
      ((= tag "MATERIAL") (if (member (strcase s) '("SUS" "SUS304" "ステンレス")) "SUS" (strcase s)))
      ((= tag "ROOM") (cond ((/= (garari:bool s) "") (garari:bool s)) (T (strcase (garari:half s)))))
      ((= tag "FLOOR") (garari:floor-name s))
      (T s)))
    (setq out (append out (list (cons tag s)))))
  (append out (list (cons "FD_TEMP" (if (= (garari:get out "FD") "あり") (cdr (assoc 'fd-temp cfg)) ""))
    (cons "MESH_SPEC" (if (= (garari:get out "MESH") "あり") (cdr (assoc 'mesh-spec cfg)) "")))))
(defun garari:issue (severity field message)
  (setq garari:issues (append garari:issues (list (list severity field message)))))
(defun garari:validate (raw norm / tag)
  (foreach tag '("GARARI" "DIA" "FD" "SHAPE" "MATERIAL" "MESH" "ROOM")
    (if (not (assoc tag raw)) (garari:issue "エラー" tag "必要タグ欠落")
      (if (= (garari:trim (garari:get raw tag)) "") (garari:issue "エラー" tag "未入力"))))
  (foreach tag '("DIA" "FD" "SHAPE" "MESH" "SOUND")
    (if (= (garari:get norm tag) "") (garari:issue "エラー" tag "不正値・非対応仕様")))
  (if (vl-string-search "\n" (garari:get norm "GARARI")) (garari:issue "エラー" "GARARI" "記号に改行")))
(defun garari:join (xs sep / s x) (setq s "")
  (foreach x xs (setq s (if (= s "") x (strcat s sep x)))) s)
(defun garari:fail (s) (setq garari:reason s) (exit))

;; Strict single-line RFC4180 fields. Embedded newlines are deliberately rejected.
(defun garari:csv-line (s / i c state field fields)
  (setq i 1 state 'start field "")
  (while (<= i (strlen s))
    (setq c (substr s i 1))
    (cond
      ((eq state 'quoted)
        (if (= c "\"")
          (if (= (substr s (1+ i) 1) "\"") (setq field (strcat field "\"") i (1+ i)) (setq state 'closed))
          (setq field (strcat field c))))
      ((= c ",") (setq fields (cons field fields) field "" state 'start))
      ((eq state 'closed) (garari:fail "CSV：閉じ引用符の後に不正文字"))
      ((= c "\"") (if (eq state 'start) (setq state 'quoted) (garari:fail "CSV：引用符の位置が不正")))
      (T (setq field (strcat field c) state 'plain)))
    (setq i (1+ i)))
  (if (eq state 'quoted) (garari:fail "CSV：引用符未完了／セル内改行は禁止"))
  (reverse (cons field fields)))
(defun garari:master-key (row) (mapcar '(lambda (k) (garari:get row k)) garari:keys))
;; Read the saved workbook in a private Excel instance. Never save the master.
(defun garari:master-path ()
  (if (null garari:directory) (garari:fail "LISPのフォルダを特定できません。main.LSPを再読込みしてください。"))
  (strcat (vl-string-right-trim "/\\" garari:directory) "/機器マスター_空調.xlsx"))
(defun garari:master-value (value)
  (if (= (type value) 'VARIANT) (setq value (vlax-variant-value value)))
  (cond ((null value) "") ((= (type value) 'STR) (garari:trim value))
    ((numberp value) (vlax-variant-value (vlax-variant-change-type (vlax-make-variant value) vlax-vbString)))
    (T (garari:fail "マスターセルの値を文字列へ変換できません。"))))
(defun garari:load-master-matrix (path sheet / books sheets ws used rows cols lastrow lastcol area result)
  (if (not (findfile path)) (garari:fail (strcat "機器マスターが存在しません：" path)))
  (if (null garari:excel)
    (progn
      (garari:progress "マスター用Excel起動")
      (setq garari:excel (garari:own (vlax-create-object "Excel.Application")))
      (garari:progress "マスター用Excel設定")
      (vlax-put-property garari:excel 'Visible :vlax-false)
      (vlax-put-property garari:excel 'DisplayAlerts :vlax-false)
      (vlax-put-property garari:excel 'EnableEvents :vlax-false)
      (vlax-put-property garari:excel 'AutomationSecurity 3)
      (garari:progress "マスター一時コピーを開く")
      (setq books (garari:own (vlax-get-property garari:excel 'Workbooks))
            garari:book (garari:own (vlax-invoke-method books 'Open path 0 :vlax-true 5 "" "" :vlax-true 2 "" :vlax-false :vlax-false)))))
  (garari:progress (strcat "マスター読取：" sheet))
  (setq sheets (garari:own (vlax-get-property garari:book 'Worksheets))
        ws (vl-catch-all-apply 'vlax-get-property (list sheets 'Item sheet)))
  (if (vl-catch-all-error-p ws) (garari:fail (strcat "マスターシートが存在しません：" sheet "\n対象Excel：" path)))
  (setq ws (garari:own ws) used (garari:own (vlax-get-property ws 'UsedRange))
        rows (garari:own (vlax-get-property used 'Rows)) cols (garari:own (vlax-get-property used 'Columns))
        lastrow (+ (vlax-get-property used 'Row) (vlax-get-property rows 'Count) -1)
        lastcol (+ (vlax-get-property used 'Column) (vlax-get-property cols 'Count) -1)
        area (garari:range ws 1 1 (max 3 lastrow) lastcol)
        result (garari:unwrap (vlax-get-property area 'Value2)))
  (if (/= (type result) 'SAFEARRAY) (garari:fail "マスターの読込み結果が配列ではありません。"))
  (vlax-safearray->list result))
(defun garari:master-matrix (path sheet / garari:excel garari:book garari:objects garari:handed garari:temp garari:file result)
  ;; Local ownership isolates master reading from output workbook ownership.
  (setq result (vl-catch-all-apply 'garari:load-master-snapshot (list path sheet)))
  (garari:cleanup)
  (if (vl-catch-all-error-p result)
    (garari:fail (if garari:reason garari:reason (strcat "マスター読込失敗：" (vl-catch-all-error-message result)))))
  result)
(defun garari:load-master-matrices (path)
  (list (garari:load-master-matrix path "GARARI_MASTER")
        (garari:load-master-matrix path "ROOM_MASTER")))
(defun garari:master-matrices (path / garari:excel garari:book garari:objects garari:handed garari:temp garari:file result)
  (setq result (vl-catch-all-apply 'garari:load-master-snapshots (list path)))
  (garari:cleanup)
  (if (vl-catch-all-error-p result)
    (garari:fail (if garari:reason garari:reason (strcat "マスター読込失敗：" (vl-catch-all-error-message result)))))
  result)
(defun garari:master-snapshot (path)
  (if (not (findfile path)) (garari:fail (strcat "機器マスターが存在しません：" path)))
  (setq garari:temp (vl-filename-mktemp "garari-master-" nil ".xlsx"))
  (if (findfile garari:temp) (vl-file-delete garari:temp))
  (if (or (not (vl-file-copy path garari:temp)) (/= (vl-file-size path) (vl-file-size garari:temp)))
    (garari:fail "機器マスターの一時コピーに失敗しました。")) garari:temp)
(defun garari:load-master-snapshot (path sheet)
  (garari:load-master-matrix (garari:master-snapshot path) sheet))
(defun garari:load-master-snapshots (path)
  (garari:load-master-matrices (garari:master-snapshot path)))
(defun garari:matrix-rows (matrix kind path / headers fields rows row required k seen key n)
  (if (null matrix) (garari:fail "空のマスター"))
  (setq headers (mapcar '(lambda (v) (strcase (garari:master-value v))) (car matrix))
    required (if (= kind "outdoor")
      (append garari:keys '("MANUFACTURER" "MODEL" "SPEC_NOTE" "APPROVED" "SOURCE_URL" "CHECKED_DATE"))
      '("MODEL" "MANUFACTURER" "DIA" "SPEC_NOTE" "APPROVED" "SOURCE_URL" "CHECKED_DATE" "AUTO_SELECT")))
  (foreach k required (if (not (member k headers)) (garari:fail (strcat "マスター必須列欠落：" k))))
  (foreach k headers (if (and (/= k "") (member k seen)) (garari:fail (strcat "マスター列重複：" k))) (setq seen (cons k seen)))
  (setq seen nil n 2)
  (foreach fields (cddr matrix)
    (setq n (1+ n))
    (setq fields (mapcar 'garari:master-value fields)
          row (mapcar 'cons headers fields))
    (if (/= (garari:get row "MODEL") "")
      (progn
        (if (/= (length fields) (length headers)) (garari:fail (strcat "マスター列数不一致：" (itoa n))))
        (if (not (member (garari:get row "APPROVED") '("0" "1"))) (garari:fail "APPROVEDは0または1"))
        (if (or (= (garari:get row "MODEL") "") (= (garari:dia (garari:get row "DIA")) "")) (garari:fail "マスター品番／径が不正"))
        (if (= kind "outdoor")
          (progn
            (foreach k '("FD" "MESH" "SOUND") (if (not (member (garari:get row k) '("あり" "なし"))) (garari:fail (strcat "マスター正規値不正：" k))))
            (if (not (member (garari:get row "SHAPE") '("深型" "平型"))) (garari:fail "マスターSHAPE不正"))
            (if (or (= (garari:get row "MATERIAL") "")
              (and (= (garari:get row "FD") "なし") (/= (garari:get row "FD_TEMP") ""))
              (and (= (garari:get row "FD") "あり") (not (garari:digits (garari:get row "FD_TEMP"))))
              (and (= (garari:get row "MESH") "なし") (/= (garari:get row "MESH_SPEC") ""))
              (and (= (garari:get row "MESH") "あり") (not (garari:digits (garari:get row "MESH_SPEC"))))) (garari:fail "マスター材質／温度／網目不正"))
            (setq key (garari:master-key row)))
          (progn
            (if (not (member (garari:get row "AUTO_SELECT") '("0" "1"))) (garari:fail "AUTO_SELECTは0または1"))
            (setq key (garari:get row "MODEL"))))
        (if (member key seen) (garari:issue "エラー" "MASTER" (strcat "マスターキー重複：" path " 行" (itoa n))))
        (setq seen (cons key seen) rows (cons row rows)))))
  (if (null rows) (garari:fail "3行目以降に有効な機器データがありません。"))
  (reverse rows))
(defun garari:read-master (path kind / sheet)
  (setq sheet (cond ((= kind "outdoor") "GARARI_MASTER") ((= kind "room") "ROOM_MASTER")
    (T (garari:fail (strcat "不明なマスター種別：" kind)))))
  (garari:matrix-rows (garari:master-matrix path sheet) kind (strcat path " / " sheet)))
(defun garari:read-masters (path / matrices)
  (setq matrices (garari:master-matrices path))
  (list (garari:matrix-rows (car matrices) "outdoor" (strcat path " / GARARI_MASTER"))
        (garari:matrix-rows (cadr matrices) "room" (strcat path " / ROOM_MASTER"))))

;; CAD extraction: editable and constant attributes, including invisible values.
(defun garari:unwrap (x) (while (= (type x) 'VARIANT) (setq x (vlax-variant-value x))) x)
(defun garari:array (x / r) (setq x (garari:unwrap x))
  (if (= (type x) 'SAFEARRAY)
    (progn (setq r (vl-catch-all-apply 'vlax-safearray->list (list x))) (if (not (vl-catch-all-error-p r)) r))
    (if (listp x) x)))
(defun garari:read-attrs (obj / method result attr tag out)
  (foreach method '(GetAttributes GetConstantAttributes)
    (setq result (vl-catch-all-apply 'vlax-invoke-method (list obj method)))
    (if (vl-catch-all-error-p result) (garari:issue "エラー" "ATTRIBUTES" (vl-catch-all-error-message result))
      (foreach attr (garari:array result)
        (setq tag (strcase (vla-get-TagString attr)))
        (if (assoc tag out) (garari:issue "エラー" tag "属性タグ重複"))
        (setq out (append out (list (cons tag (vla-get-TextString attr)))))
        (vlax-release-object attr)))) out)
(defun garari:name (o / r) (setq r (vl-catch-all-apply 'vlax-get-property (list o 'EffectiveName)))
  (if (vl-catch-all-error-p r) (vla-get-Name o) r))
(defun garari:target (e / d o yes block)
  (setq d (entget e))
  (if (and (= (cdr (assoc 0 d)) "INSERT") (= (cdr (assoc 410 d)) "Model")
    (<= (if (assoc 70 d) (cdr (assoc 70 d)) 1) 1)
    (<= (if (assoc 71 d) (cdr (assoc 71 d)) 1) 1))
    (progn (setq o (vlax-ename->vla-object e))
      (setq block (tblsearch "BLOCK" (vla-get-Name o)))
      (setq yes (and (= (strcase (garari:name o)) "GARARI")
        (= 0 (logand 4 (if (assoc 70 block) (cdr (assoc 70 block)) 0)))
        (not (= (vla-get-ObjectName o) "AcDbMInsertBlock"))))
      (vlax-release-object o))) yes)
(defun garari:select-model (norm master / found row)
  (foreach row master (if (and (= (garari:get row "APPROVED") "1") (equal (garari:master-key norm) (garari:master-key row)))
    (setq found (cons row found))))
  (cond ((= (length found) 1) (car found))
    ((null found) (garari:issue "警告" "MODEL" (strcat "選定未登録：" (garari:join (garari:master-key norm) "/"))) nil)
    (T (garari:issue "エラー" "MODEL" "承認済みマスター競合") nil)))
(defun garari:record (raw trace master rooms cfg / garari:issues norm outdoor indoor found room row)
  (setq garari:issues (garari:get trace "ISSUES") norm (garari:normalize raw cfg))
  (garari:validate raw norm)
  (if (/= (garari:get norm "FLOOR") "")
    (progn
      (if (and (/= (garari:get trace "SELECT_FLOOR") "") (/= (garari:get trace "SELECT_FLOOR") (garari:get norm "FLOOR"))) (garari:issue "警告" "FLOOR" "選択階とFLOOR属性が異なる（属性を優先）"))
      (setq trace (garari:set trace "FLOOR" (garari:get norm "FLOOR")))))
  (if (= (garari:get trace "FLOOR") "") (progn (setq trace (garari:set trace "FLOOR" "階未設定")) (garari:issue "警告" "FLOOR" "階未設定")))
  (setq outdoor (garari:select-model norm master) room (garari:get norm "ROOM"))
  (cond
    ((= room "あり")
      (foreach row rooms
        (if (and (= (garari:get row "MANUFACTURER") "三菱電機")
          (= (garari:get row "DIA") (garari:get norm "DIA"))
          (= (garari:get row "APPROVED") "1") (= (garari:get row "AUTO_SELECT") "1"))
          (setq found (cons row found))))
      (cond ((= (length found) 1) (setq indoor (car found)))
        ((null found) (garari:issue "警告" "ROOM" "室内給気口：要選定"))
        (T (garari:issue "エラー" "ROOM" "室内給気口：既定マスター競合"))))
    ((not (member room '("" "なし")))
      (garari:issue "警告" "ROOM" "旧ROOM品番形式：新規入力はあり／なし")
      (foreach row rooms (if (= (strcase (garari:half (garari:get row "MODEL"))) room) (setq found (cons row found))))
      (cond ((> (length found) 1) (garari:issue "エラー" "ROOM" "室内マスター競合"))
        ((or (null found) (/= (garari:get (car found) "APPROVED") "1")) (garari:issue "警告" "ROOM" "室内給気口仕様・適用径要確認"))
        ((/= (garari:get (car found) "DIA") (garari:get norm "DIA")) (garari:issue "エラー" "ROOM" "室内給気口の適用径不一致"))
        (T (setq indoor (car found))))))
  (if (not (member room '("" "なし"))) (garari:issue "警告" "ROOM" "セットの組合せ・施工適合要確認"))
  (append (list (cons "RAW" raw) (cons "NORM" norm) (cons "OUTDOOR" outdoor) (cons "INDOOR" indoor)
    (cons "ISSUES" garari:issues)) (vl-remove-if '(lambda (x) (= (car x) "ISSUES")) trace)))
(defun garari:add-record-issue (r level field message)
  (garari:set r "ISSUES" (append (garari:get r "ISSUES") (list (list level field message)))))
(defun garari:extract (e floor master rooms cfg / o raw trace garari:issues point r)
  (setq o (vlax-ename->vla-object e) raw (garari:read-attrs o) point (garari:array (vla-get-InsertionPoint o)))
  (setq trace (list (cons "DWG" (strcat (getvar "DWGPREFIX") (getvar "DWGNAME")))
    (cons "HANDLE" (vla-get-Handle o)) (cons "NAME" (garari:name o)) (cons "LAYER" (vla-get-Layer o))
    (cons "POINT" point) (cons "SELECT_FLOOR" floor) (cons "FLOOR" floor) (cons "ISSUES" garari:issues)))
  (vlax-release-object o) (garari:record raw trace master rooms cfg))
(defun garari:signature (r / n) (setq n (garari:get r "NORM"))
  (mapcar '(lambda (k) (garari:get n k)) (append '("DIA" "FD" "SHAPE" "MATERIAL" "MESH" "ROOM") '("MESH_SPEC" "FD_TEMP" "SOUND"))))
(defun garari:symbol (r / s) (setq s (garari:get (garari:get r "NORM") "GARARI"))
  (if (or (= s "") (vl-string-search "\n" s)) (strcat "未設定@" (garari:get r "HANDLE")) s))
(defun garari:cross-check (records / out r other conflict duplicate)
  (foreach r records
    (setq conflict nil duplicate nil)
    (foreach other records
      (if (/= (garari:get r "HANDLE") (garari:get other "HANDLE"))
        (progn
          (if (and (= (garari:symbol r) (garari:symbol other)) (not (equal (garari:signature r) (garari:signature other)))) (setq conflict T))
          (if (equal (garari:get r "POINT") (garari:get other "POINT") 1e-8) (setq duplicate T)))))
    (if conflict (setq r (garari:add-record-issue r "警告" "GARARI" "同一記号の仕様不一致")))
    (if duplicate (setq r (garari:add-record-issue r "警告" "POINT" "同一座標の重複候補（数量を保持）")))
    (setq out (append out (list r)))) out)
(defun garari:less (a b / x y dx dy)
  (setq x (car a) y (car b) dx (garari:digits x) dy (garari:digits y))
  (cond ((and dx dy) (if (= (atof x) (atof y)) (< x y) (< (atof x) (atof y))))
    (dx T) (dy nil)
    ((and (wcmatch x "[a-zA-Z]*") (not (wcmatch y "[a-zA-Z]*"))) T)
    ((and (wcmatch y "[a-zA-Z]*") (not (wcmatch x "[a-zA-Z]*"))) nil)
    (T (< x y))))
(defun garari:stable-sort (items predicate / indexed i item)
  (setq i 0)
  (foreach item items (setq indexed (append indexed (list (cons i item))) i (1+ i)))
  (mapcar 'cdr (vl-sort indexed '(lambda (a b)
    (cond ((apply predicate (list (cdr a) (cdr b))) T)
      ((apply predicate (list (cdr b) (cdr a))) nil) (T (< (car a) (car b))))))))
(defun garari:aggregate (records / groups key pair r)
  (foreach r records
    (setq key (cons (garari:symbol r) (garari:signature r)) pair (assoc key groups))
    (if pair (setq groups (subst (cons key (append (cdr pair) (list r))) pair groups))
      (setq groups (append groups (list (cons key (list r)))))))
  (if (eq (cdr (assoc 'order garari:config)) 'input) groups
    ;; sort indices preserves rows with identical symbols and different specifications
    (garari:stable-sort groups '(lambda (a b) (garari:less (car a) (car b))))))
(defun garari:floor-rank (s / x) (setq x (strcase s))
  (cond ((and (> (strlen x) 2) (= (substr x 1 1) "B") (= (substr x (strlen x)) "F") (garari:digits (substr x 2 (- (strlen x) 2)))) (- (atoi (substr x 2))))
    ((and (> (strlen x) 1) (= (substr x (strlen x)) "F") (garari:digits (substr x 1 (1- (strlen x))))) (atoi x))
    ((= x "RF") 10000) ((= x "階未設定") 10002) (T 10001)))
(defun garari:floors (records / out r)
  (foreach r records (if (not (member (garari:get r "FLOOR") out)) (setq out (append out (list (garari:get r "FLOOR"))))))
  (garari:stable-sort out '(lambda (a b) (< (garari:floor-rank a) (garari:floor-rank b)))))
(defun garari:state (r / s issue) (setq s "正常")
  (foreach issue (garari:get r "ISSUES")
    (cond ((= (car issue) "エラー") (setq s "エラー")) ((and (= s "正常") (= (car issue) "警告")) (setq s "要確認")))) s)
(defun garari:notes (records / xs r issue x)
  (foreach r records (foreach issue (garari:get r "ISSUES") (setq x (caddr issue)) (if (not (member x xs)) (setq xs (append xs (list x))))))
  (garari:join xs "／"))
(defun garari:spec-note (s)
  ;; Keep technical/installation notes; omit known master drafting history.
  (setq s (vl-string-subst "" "大佐DS-VAND10Mから変更。" s))
  (garari:trim (if (= s "フラットカバー付BSW-SB初期案") "フラットカバー付BSW-SB" s)))
(defun garari:issue-count (records global severity / count r issue)
  (setq count 0)
  (foreach issue global (if (= (car issue) severity) (setq count (1+ count))))
  (foreach r records
    (foreach issue (garari:get r "ISSUES") (if (= (car issue) severity) (setq count (1+ count)))))
  count)
(defun garari:spec (r / n indoor s)
  (setq n (garari:get r "NORM") indoor (garari:get r "INDOOR"))
  (setq s (strcat (if (= (garari:get n "DIA") "") "径要確認" (strcat (garari:get n "DIA") "φ")) "、"
    (cond ((= (garari:get n "FD") "あり") (strcat "FD付き（" (garari:get n "FD_TEMP") "℃）")) ((= (garari:get n "FD") "なし") "FDなし") (T "FD要確認"))
    "、" (garari:get n "MATERIAL") "、"
    (cond ((= (garari:get n "MESH") "あり") (strcat "防虫網付き（" (garari:get n "MESH_SPEC") "メッシュ）")) ((= (garari:get n "MESH") "なし") "防虫網なし") (T "網要確認"))
    (if (= (garari:get n "SOUND") "あり") "、防音型" "")))
  (if indoor (setq s (strcat s "\n室内：" (garari:get indoor "SPEC_NOTE"))))
  (if (garari:get r "OUTDOOR") (setq s (strcat s "\n" (garari:spec-note (garari:get (garari:get r "OUTDOOR") "SPEC_NOTE"))))) s)

;; Excel objects belong solely to a new application; release every child reference.
(defun garari:own (x) (setq x (garari:unwrap x))
  (setq garari:objects (cons x garari:objects)) x)
(defun garari:drop (x) (vlax-release-object x) (setq garari:objects (vl-remove x garari:objects)))
(defun garari:close-book (book) (vlax-invoke-method book 'Close :vlax-false "" :vlax-false))
(defun garari:open-book (books path)
  (vlax-invoke-method books 'Open path 0 :vlax-false 5 "" "" :vlax-true 2 "" :vlax-false :vlax-false 0 :vlax-false :vlax-true 0))
(defun garari:progress (stage)
  (setq garari:stage stage) (princ (strcat "\nGARARITABLE：" stage)))
(defun garari:owner-file (path)
  (strcat (vl-filename-directory path) "\\~$" (vl-filename-base path) (vl-filename-extension path)))
(defun garari:check-available (path)
  ;; Do not query another Excel instance: a modal dialog there can block COM.
  ;; An owner file may be stale; never remove it automatically.
  (if (findfile (garari:owner-file path))
    (garari:fail "対象Excelのロックファイルがあります。対象ブックを保存して閉じてから再実行してください。閉じても出る場合は残存ロックを確認してください。")))
(defun garari:cleanup (/ x)
  (if garari:file (progn (close garari:file) (setq garari:file nil)))
  ;; Release ranges, sheets and collections while their Excel server is alive.
  ;; Releasing stale child proxies after Quit can block with another Excel open.
  (foreach x garari:objects
    (if (and (not (eq x garari:book)) (not (eq x garari:excel)))
      (vl-catch-all-apply 'vlax-release-object (list x))))
  (setq garari:objects nil)
  (if garari:excel
    (progn
      (if (not garari:handed)
        (progn
          ;; Keep private-instance prompts suppressed until Close and Quit finish.
          (vl-catch-all-apply 'vlax-put-property (list garari:excel 'DisplayAlerts :vlax-false))
          (if garari:book (vl-catch-all-apply 'garari:close-book (list garari:book)))))
      (if garari:book (vl-catch-all-apply 'vlax-release-object (list garari:book)))
      (if (not garari:handed) (vl-catch-all-apply 'vlax-invoke-method (list garari:excel 'Quit)))
      (vl-catch-all-apply 'vlax-release-object (list garari:excel))))
  (setq garari:objects nil garari:book nil garari:excel nil)
  ;; Explicit releases suffice; forced GC immediately after Quit can stall COM.
  (if (and garari:temp (findfile garari:temp)) (vl-file-delete garari:temp)))
(defun garari:col (n / s) (setq s "")
  (while (> n 0) (setq n (1- n) s (strcat (chr (+ 65 (rem n 26))) s) n (fix (/ n 26)))) s)
(defun garari:range (sheet r1 c1 r2 c2)
  (garari:own (vlax-get-property sheet 'Range (strcat (garari:col c1) (itoa r1)) (strcat (garari:col c2) (itoa r2)))))
(defun garari:put-matrix (sheet row data) (garari:put-matrix-at sheet row 1 data))
(defun garari:put-matrix-at (sheet row col data / area arr nr nc)
  (if data
    (progn
      (setq nr (length data) nc (length (car data)) area (garari:range sheet row col (+ row nr -1) (+ col nc -1)))
      (vlax-put-property area 'NumberFormat "@")
      (setq arr (vlax-make-safearray vlax-vbVariant (cons 1 nr) (cons 1 nc)))
      ;; Excel literal prefix also prevents external strings becoming formulas.
      (vlax-safearray-fill arr (mapcar '(lambda (xs) (mapcar '(lambda (v) (if (= (type v) 'STR) (strcat "'" v) v)) xs)) data))
      (vlax-put-property area 'Value2 (vlax-make-variant arr)) (garari:drop area))))
(defun garari:format (sheet lastrow lastcol / area font borders columns i width)
  (setq area (garari:range sheet 1 1 lastrow lastcol))
  (vlax-put-property area 'WrapText :vlax-true) (vlax-put-property area 'VerticalAlignment -4108)
  (vlax-put-property area 'HorizontalAlignment -4131)
  (setq font (garari:own (vlax-get-property area 'Font))) (vlax-put-property font 'Size 10) (garari:drop font)
  (setq borders (garari:own (vlax-get-property area 'Borders))) (vlax-put-property borders 'LineStyle 1) (vlax-put-property borders 'Weight 2) (garari:drop borders)
  (garari:drop area)
  (setq area (garari:range sheet 1 1 1 lastcol) font (garari:own (vlax-get-property area 'Font)))
  (vlax-put-property font 'Bold :vlax-true) (vlax-put-property area 'RowHeight 30)
  (garari:drop font) (garari:drop area))
(defun garari:sheet (sheets name / s) (setq s (garari:own (vlax-invoke-method sheets 'Add))) (vla-put-Name s name) s)
(defun garari:raw-data (records / header data r n raw tag pt)
  (setq header '("DWG" "HANDLE" "EffectiveName" "LAYER" "X" "Y" "Z" "選択階" "階" "状態" "屋外品番" "室内品番" "エラー" "全原属性（重複含む）"))
  (foreach tag garari:tags (setq header (append header (list (strcat "RAW_" tag) (strcat "NORM_" tag)))))
  (setq header (append header '("MESH_SPEC" "FD_TEMP" "室内メーカー" "室内仕様")) data (list header))
  (foreach r records
    (setq n (garari:get r "NORM") raw (garari:get r "RAW") pt (garari:get r "POINT"))
    (setq data (append data (list (append
      (list (garari:get r "DWG") (garari:get r "HANDLE") (garari:get r "NAME") (garari:get r "LAYER")) pt
      (list (garari:get r "SELECT_FLOOR") (garari:get r "FLOOR") (garari:state r)
        (if (garari:get r "OUTDOOR") (garari:get (garari:get r "OUTDOOR") "MODEL") "要選定")
        (garari:room-model r) (garari:notes (list r)) (vl-prin1-to-string raw))
      (apply 'append (mapcar '(lambda (k) (list (garari:get raw k) (garari:get n k))) garari:tags))
      (list (garari:get n "MESH_SPEC") (garari:get n "FD_TEMP")
        (garari:get (garari:get r "INDOOR") "MANUFACTURER") (garari:get (garari:get r "INDOOR") "SPEC_NOTE"))))))) data)
(defun garari:error-data (records global / data r issue)
  (setq data (list '("区分" "GARARI" "ハンドル" "レイヤ" "X" "Y" "Z" "項目" "原因")))
  (foreach issue global (setq data (append data (list (append (list (car issue) "" "" "") '("" "" "") (cdr issue))))))
  (foreach r records
    (if (null (garari:get r "ISSUES"))
      (setq data (append data (list (append (list "正常" (garari:symbol r) (garari:get r "HANDLE") (garari:get r "LAYER")) (garari:get r "POINT") '("" "")))))
      (foreach issue (garari:get r "ISSUES")
        (setq data (append data (list (append (list (car issue) (garari:symbol r) (garari:get r "HANDLE") (garari:get r "LAYER")) (garari:get r "POINT") (cdr issue)))))))) data)
(defun garari:table-plan (groups floors / rows blocks g r n outdoor indoor room maker start end vals f count notes)
  (setq rows (list (append '("記号" "名称" "参考型番" "機器仕様") floors '("数量" "備考"))))
  (foreach g groups
    (setq r (cadr g) n (garari:get r "NORM") outdoor (garari:get r "OUTDOOR") indoor (garari:get r "INDOOR") room (garari:get n "ROOM"))
    (setq maker (if outdoor (garari:get outdoor "MANUFACTURER") "屋外メーカー要確認"))
    (if (not (member room '("なし" ""))) (setq maker (strcat "屋外：" maker "／室内：" (if indoor (garari:get indoor "MANUFACTURER") "要確認"))))
    (setq vals nil)
    (foreach f floors (setq count 0) (foreach r (cdr g) (if (= (garari:get r "FLOOR") f) (setq count (1+ count)))) (setq vals (append vals (list count))))
    (setq r (cadr g) start (1+ (length rows)) notes (garari:notes (cdr g)))
    (setq rows (append rows (list (append
      (list (caar g) (if (member room '("なし" "")) "ガラリ" "自然給気口＋ガラリ") maker (garari:spec r)) vals
      (list (length (cdr g)) (strcat (garari:get n "SHAPE") (if (= notes "") "" (strcat "／" notes))))))))
    (setq rows (append rows (list (append (list "" "" (strcat "屋外：" (if outdoor (garari:get outdoor "MODEL") "要選定")) "") (mapcar '(lambda (x) "") floors) '("" "")))))
    (if (not (member room '("なし" "")))
      (setq rows (append rows (list (append (list "" "" (strcat "室内：" (garari:room-model r)) "") (mapcar '(lambda (x) "") floors) '("" ""))))))
    (setq end (length rows) blocks (append blocks (list (list start end)))))
  (list rows blocks))
(defun garari:text-height (s width / chars lines c)
  (setq chars 0 lines 1)
  (foreach c (vl-string->list s)
    (if (= c 10) (setq lines (1+ lines) chars 0)
      (progn (setq chars (+ chars (if (> c 255) 2 1))) (if (> chars width) (setq lines (1+ lines) chars 0)))))
  (+ 12 (* 14 lines)))
(defun garari:write-xlsx (path records groups floors settings global / books sheets table raw errors setup plan rows blocks lastcol widths width col area block start end ht used row vals i page breakobj breaks fresh targets backup garari:backup-error)
  (setq path (vl-string-translate "/" "\\" path))
  (garari:progress "対象ファイルのロック確認")
  (garari:check-available path)
  (garari:progress "専用Excel起動")
  (setq garari:excel (garari:own (vlax-create-object "Excel.Application")))
  (vlax-put-property garari:excel 'Visible :vlax-false)
  (vlax-put-property garari:excel 'DisplayAlerts :vlax-false)
  (vlax-put-property garari:excel 'EnableEvents :vlax-false)
  (vlax-put-property garari:excel 'AutomationSecurity 3)
  (vlax-put-property garari:excel 'ScreenUpdating :vlax-false)
  (garari:progress "対象ブックを開く")
  (setq books (garari:own (vlax-get-property garari:excel 'Workbooks))
    garari:book (garari:own (garari:open-book books path)))
  (if (= (vlax-get-property garari:book 'ReadOnly) :vlax-true)
    (garari:fail "対象Excelは読み取り専用または使用中です。保存して閉じた後に再実行してください。"))
  (if (vlax-property-available-p garari:book 'AutoSaveOn)
    (if (= (vlax-get-property garari:book 'AutoSaveOn) :vlax-true)
      (vlax-put-property garari:book 'AutoSaveOn :vlax-false)))
  (garari:progress "出力先・管理範囲を確認")
  (setq sheets (garari:own (vlax-get-property garari:book 'Worksheets))
    plan (garari:table-plan groups floors) rows (car plan) lastcol (+ 6 (length floors)))
  ;; Resolve ALL destinations before backing up or writing any cells.
  (setq targets (list
    (garari:destination sheets (cdr (assoc 'table-sheet garari:config)) "_GARARI_TABLE" rows)
    (garari:destination sheets "GARARI_CAD_DATA" "_GARARI_DATA" (garari:raw-data records))
    (garari:destination sheets "GARARI_エラー一覧" "_GARARI_ERRORS" (garari:error-data records global))
    (garari:destination sheets "GARARI_選定設定" "_GARARI_SETUP" (cons '("設定項目" "値") settings))))
  (garari:progress "バックアップ作成")
  (setq backup (garari:backup-path path))
  (if (or (not (garari:copy-backup path backup)) (/= (vl-file-size path) (vl-file-size backup)))
    (garari:fail (strcat "バックアップ作成失敗。書き込みは開始していません。"
      "\nコピー元：" path "\n保存先：" backup
      "\n詳細：" (if garari:backup-error garari:backup-error "コピー失敗またはファイルサイズ不一致"))))
  (princ (strcat "\nバックアップ：" backup))
  (setq fresh (not (car (car targets))))
  (garari:progress "管理範囲書込")
  (foreach area targets (garari:write-destination sheets area))
  (setq table (garari:own (vlax-get-property sheets 'Item (cdr (assoc 'table-sheet garari:config)))))
  (garari:merge-table table (nth 3 (car targets)) (cadr plan) lastcol)
  ;; Existing templates retain styles, widths, heights and print settings.
  (if fresh (progn
  (setq garari:stage "表データ")
  (setq plan (garari:table-plan groups floors) rows (car plan) blocks (cadr plan) lastcol (+ 6 (length floors)))
  (garari:format table (length rows) lastcol)
  (setq garari:stage "列幅")
  (setq widths (append (cdr (assoc 'widths garari:config)) (mapcar '(lambda (x) (cdr (assoc 'floor-width garari:config))) floors)
    (list (cdr (assoc 'floor-width garari:config)) (cdr (assoc 'note-width garari:config)))) col 1)
  (foreach ht widths (setq area (garari:range table 1 col (length rows) col))
    (vlax-put-property area 'ColumnWidth ht)
    (if (or (= col 1) (and (> col 4) (< col lastcol))) (vlax-put-property area 'HorizontalAlignment -4108))
    (if (and (> col 4) (< col lastcol)) (vlax-put-property area 'NumberFormat "0"))
    (garari:drop area) (setq col (1+ col)))
  (setq used 30 breaks (garari:own (vlax-get-property table 'HPageBreaks)))
  (setq garari:stage "結合・行高")
  (foreach block blocks
    (setq start (car block) end (cadr block) vals (nth (1- start) rows) ht 30 i 0)
    (foreach width widths
      (if (= (type (nth i vals)) 'STR) (setq ht (max ht (garari:text-height (nth i vals) width))))
      (setq i (1+ i)))
    (setq row start)
    (while (<= row end) (setq ht (max ht (* (- end start -1) (garari:text-height (nth 2 (nth (1- row) rows)) (nth 2 widths))))) (setq row (1+ row)))
    (if (> ht (- (cdr (assoc 'page-height garari:config)) 30)) (garari:fail "1機器がA3ページ高さを超えます。列幅設定を調整してください。"))
    (if (> (+ used ht) (cdr (assoc 'page-height garari:config)))
      (progn (setq area (garari:range table start 1 start 1))
        (setq breakobj (garari:own (vlax-invoke-method breaks 'Add area))) (garari:drop breakobj) (garari:drop area) (setq used 30)))
    (setq area (garari:range table start 1 end lastcol)) (vlax-put-property area 'RowHeight (/ ht (- end start -1))) (garari:drop area)
    (setq col 1)
    (repeat lastcol
      (if (/= col 3) (progn (setq area (garari:range table start col end col)) (vlax-invoke-method area 'Merge) (garari:drop area)))
      (setq col (1+ col)))
    (setq used (+ used ht)))
  (setq page (garari:own (vlax-get-property table 'PageSetup)))
  (setq garari:stage "印刷設定")
  (vlax-put-property page 'PaperSize 8) (vlax-put-property page 'Orientation 2)
  (vlax-put-property page 'Zoom :vlax-false) (vlax-put-property page 'FitToPagesWide 1) (vlax-put-property page 'FitToPagesTall :vlax-false)
  (vlax-put-property page 'PrintTitleRows "$1:$1")
  (vlax-put-property page 'PrintArea (strcat "$A$1:$" (garari:col lastcol) "$" (itoa (length rows))))
  (vlax-put-property page 'TopMargin 28) (vlax-put-property page 'BottomMargin 28)
  (garari:drop page)
  ))
  (vlax-invoke-method table 'Activate)
  (garari:progress "保存")
  (vlax-invoke-method garari:book 'Save)
  (if (/= (vlax-get-property garari:book 'Saved) :vlax-true) (garari:fail "Excel保存を確認できません。バックアップを保持しています。"))
  (setq garari:saved T)
  ;; Close and reopen before declaring success; no application owned by the user is touched.
  (garari:progress "保存済みブックの再オープン確認")
  (garari:close-book garari:book) (setq garari:book nil)
  (setq garari:book (garari:own (garari:open-book books path)))
  (if (cdr (assoc 'show-result garari:config))
    (progn (garari:progress "結果をExcelで表示")
      (vlax-put-property garari:excel 'DisplayAlerts :vlax-true)
      (vlax-put-property garari:excel 'ScreenUpdating :vlax-true)
      (vlax-put-property garari:excel 'EnableEvents :vlax-true)
      (vlax-put-property garari:excel 'Visible :vlax-true) (setq garari:handed T))) T)

(defun garari:output-path (extension / base path)
  (setq base (strcat (getvar "DWGPREFIX") (vl-filename-base (getvar "DWGNAME")) "_ガラリ機器表." extension))
  (if (findfile base) (setq base (vl-filename-mktemp "ガラリ機器表-" (getvar "DWGPREFIX") (strcat "." extension))))
  (setq path (getfiled "ガラリ機器表：新規保存（既存ファイル不可）" base extension 1))
  (while (and path (findfile path)) (princ "\n既存ファイルです。別名を指定してください。") (setq path (getfiled "別名保存" base extension 1))) path)
(defun garari:csv-quote (s / i out c) (if (/= (type s) 'STR) (setq s (vl-princ-to-string s)))
  (setq i 1 out "\"") (while (<= i (strlen s)) (setq c (substr s i 1) out (strcat out (if (= c "\"") "\"\"" c)) i (1+ i))) (strcat out "\""))
(defun garari:write-csv (path records / f row s)
  (setq garari:temp (vl-filename-mktemp "garari-stage-" (vl-filename-directory path) ".csv") f (open garari:temp "w" "utf8-bom") garari:file f)
  (if (not f) (garari:fail "代替CSVの保存失敗"))
  (foreach row (garari:raw-data records)
    (write-line (garari:join (mapcar '(lambda (v) (if (and (= (type v) 'STR) (member (substr v 1 1) '("=" "+" "-" "@"))) (setq v (strcat "'" v))) (garari:csv-quote v)) row) ",") f))
  (close f) (setq garari:file nil)
  (if (or (findfile path) (not (vl-file-rename garari:temp path))) (garari:fail "CSV別名保存失敗")) (setq garari:temp nil))
(defun c:GARARIMASTERSET (/ *error* garari:reason garari:issues path masters)
  ;; Compatibility command: validate the fixed workbook instead of selecting CSVs.
  (defun *error* (msg)
    (princ (strcat "\nGARARIMASTERSET：" (if garari:reason garari:reason msg))) (princ))
  (if (= (getvar "LISPSYS") 0) (garari:fail "LISPSYS=1または2で実行してください。"))
  (setq path (garari:master-path) masters (garari:read-masters path))
  (princ (strcat "\n統合マスター：" path
    "\nGARARI_MASTER=" (itoa (length (car masters)))
    " / ROOM_MASTER=" (itoa (length (cadr masters)))
    "\nマスター警告／エラー=" (itoa (length garari:issues)))) (princ))
(defun garari:summary (records groups floors excluded / normal warning errors r f qty)
  (setq normal 0 warning 0 errors 0 qty 0)
  (foreach r records (cond ((= (garari:state r) "正常") (setq normal (1+ normal))) ((= (garari:state r) "エラー") (setq errors (1+ errors))) (T (setq warning (1+ warning)))))
  (foreach r groups (setq qty (+ qty (length (cdr r)))))
  (if (/= qty (length records)) (garari:fail "集計数量と採用数が一致しません"))
  (princ (strcat "\n採用ユニークブロック=" (itoa (length records)) " 正常=" (itoa normal) " 要確認=" (itoa warning) " エラー=" (itoa errors) " 数量合計=" (itoa qty) " 選択対象外=" (itoa excluded)))
  (foreach f floors (setq qty 0) (foreach r records (if (= (garari:get r "FLOOR") f) (setq qty (1+ qty)))) (princ (strcat "\n" f "=" (itoa qty))))
  (princ "\n対象外：ペーパー空間・Xref内・入れ子・MINSERT。モデル空間の凡例は手動で除外。"))
;; Canonical floors and bounded range parser. No layer/coordinate inference.
(defun garari:compact (s / out c)
  (setq out "")
  (foreach c (vl-string->list (strcase (garari:half s)))
    (if (not (member c '(9 32 12288))) (setq out (strcat out (chr c))))) out)
(defun garari:floor-name (s / x n)
  (setq x (garari:compact s))
  (cond ((= x "") "") ((garari:digits x) (strcat (itoa (atoi x)) "F"))
    ((and (> (strlen x) 1) (= (substr x (strlen x)) "F") (garari:digits (substr x 1 (1- (strlen x))))) (strcat (itoa (atoi x)) "F"))
    ((and (> (strlen x) 2) (= (substr x 1 1) "B") (= (substr x (strlen x)) "F") (garari:digits (substr x 2 (- (strlen x) 2)))) (strcat "B" (itoa (atoi (substr x 2))) "F"))
    (T x)))
(defun garari:split (s sep / pos out)
  (while (setq pos (vl-string-search sep s))
    (setq out (append out (list (substr s 1 pos))) s (substr s (+ pos 2))))
  (append out (list s)))
(defun garari:parse-floors (s / x parts part pair a b n out valid f)
  (setq x (garari:compact s) valid T)
  (setq x (vl-string-translate "，、～〜－–—" ",,-----" x))
  (foreach part (garari:split x ",")
    (cond
      ((vl-string-search "-" part)
        (setq pair (garari:split part "-"))
        (if (= (length pair) 2)
          (progn
            (setq a (garari:floor-name (car pair)) b (garari:floor-name (cadr pair)))
            (if (and (wcmatch a "#*F") (wcmatch b "#*F")
              (garari:digits (substr a 1 (1- (strlen a)))) (garari:digits (substr b 1 (1- (strlen b))))
              (> (atoi a) 0) (>= (atoi b) (atoi a)) (<= (atoi b) 999))
              (progn (setq n (atoi a)) (while (<= n (atoi b))
                (setq f (strcat (itoa n) "F")) (if (not (member f out)) (setq out (append out (list f)))) (setq n (1+ n))))
              (setq valid nil)))
          (setq valid nil)))
      ((= part "") (setq valid nil))
      (T (setq f (garari:floor-name part))
        (if (or (= f "RF")
          (and (= (substr f (strlen f)) "F")
            (setq a (if (= (substr f 1 1) "B") (substr f 2 (- (strlen f) 2)) (substr f 1 (1- (strlen f)))))
            (garari:digits a) (> (atoi a) 0) (<= (atoi a) 999)))
          (if (not (member f out)) (setq out (append out (list f))))
          (setq valid nil)))))
  (if valid out))
(defun garari:room-model (r / room indoor)
  (setq room (garari:get (garari:get r "NORM") "ROOM") indoor (garari:get r "INDOOR"))
  (cond (indoor (garari:get indoor "MODEL")) ((= room "あり") "要選定")
    ((member room '("なし" "")) "") (T room)))
(defun garari:selection (floor master rooms cfg records seen requested / retry ss i e h pair r count excluded value)
  (setq retry T excluded 0)
  (while retry
    (setq count 0)
    (princ (if (= floor "") "\n複数階の図面をまとめて選択（FLOOR属性で割当）：" (strcat "\n" floor " の範囲を選択：")))
    (setq ss (ssget))
    (if ss (progn (setq i 0) (repeat (sslength ss)
      (setq e (ssname ss i) i (1+ i))
      (if (garari:target e)
        (progn
          (setq count (1+ count) h (cdr (assoc 5 (entget e))) pair (assoc h seen))
          (if pair
            (if (/= (cdr pair) floor)
              (progn (setq r (car (vl-remove-if-not '(lambda (x) (= (garari:get x "HANDLE") h)) records)))
                (setq records (subst (garari:add-record-issue r "エラー" "FLOOR" "別階で再選択：階割当競合（最初の割当を保持）") r records))))
            (progn
              (setq r (garari:extract e floor master rooms cfg))
              (if (not (member (garari:get r "FLOOR") requested))
                (setq r (garari:add-record-issue r "警告" "FLOOR" "FLOOR未設定または指定外：追跡・追加階列へ保持")))
              (setq records (append records (list r)) seen (cons (cons h floor) seen)))))
        (setq excluded (1+ excluded))))))
    (princ (strcat "\n選択GARARI=" (itoa count) " / 採用ユニーク累計=" (itoa (length records)) " / 除外要素=" (itoa excluded)))
    (setq retry nil)
    (if (= count 0)
      (progn
        (princ "\n対象GARARIがありません。")
        (initget "Retry Skip Exit") (setq value (getkword "\n[Retry(再選択)/Skip(0台として次へ)/Exit(終了)] <Retry>："))
        (cond ((= value "Exit") (garari:fail "選択終了（Excel未変更）")) ((= value "Skip") nil) (T (setq retry T))))))
  (list records seen excluded))
;; Project path persists separately from the tool repository search path pa-path.
(defun c:GARARIPROJECTSET (/ shell folder item path)
  (setq shell (vlax-create-object "Shell.Application"))
  (setq folder (vlax-invoke-method shell 'BrowseForFolder 0 "プロジェクトExcelの初期フォルダ" 1))
  (if folder
    (progn (setq item (vlax-get-property folder 'Self) path (vlax-get-property item 'Path))
      (if (vl-file-directory-p path) (progn (setenv "GARARI_PROJECT_DIR" path) (princ (strcat "\nprojectフォルダ：" path))))
      (vlax-release-object item) (vlax-release-object folder)))
  (vlax-release-object shell) (princ))
(defun garari:project-book (/ dir path)
  (setq dir (getenv "GARARI_PROJECT_DIR"))
  (if (and (or (null dir) (not (vl-file-directory-p dir)))
    (boundp 'PROJECT_DIR) (= (type PROJECT_DIR) 'STR) (vl-file-directory-p PROJECT_DIR))
    (progn (setq dir PROJECT_DIR) (setenv "GARARI_PROJECT_DIR" dir)))
  (if (or (null dir) (not (vl-file-directory-p dir)))
    (progn (princ "\nprojectフォルダが未設定または存在しません。フォルダを選択してください。")
      (c:GARARIPROJECTSET) (setq dir (getenv "GARARI_PROJECT_DIR"))))
  (if (and dir (vl-file-directory-p dir))
    (progn
      (setq path (getfiled "更新する既存プロジェクトExcelを選択" (strcat (vl-string-right-trim "/\\" dir) "\\") "xlsx" 0))
      (if (and path (/= (strcase (vl-filename-extension path)) ".XLSX")) (garari:fail "初期対応は.xlsxのみです。"))
      (if (and path (not (findfile path))) (garari:fail "対象Excelが存在しません。")) path)))
(defun garari:backup-path (path / base candidate n)
  (setq base (strcat (vl-filename-directory path) "/" (vl-filename-base path) "_GARARI_backup-"
    (vl-string-translate "." "_" (rtos (getvar "CDATE") 2 8))) candidate (strcat base ".xlsx") n 0)
  (while (findfile candidate) (setq n (1+ n) candidate (strcat base "-" (itoa n) ".xlsx"))) candidate)
;; Use the Windows Unicode copy API through FSO for OneDrive/reparse-point files.
;; Copy the saved bytes, not SaveCopyAs (which can reserialize the workbook).
;; Never overwrite a previous backup; release FSO even when CopyFile fails.
(defun garari:copy-backup-file (path backup / fso result size)
  (setq garari:backup-error nil
    path (vl-string-translate "/" "\\" path)
    backup (vl-string-translate "/" "\\" backup)
    fso (vl-catch-all-apply 'vlax-create-object (list "Scripting.FileSystemObject")))
  (if (vl-catch-all-error-p fso)
    (progn (setq garari:backup-error (vl-catch-all-error-message fso)) nil)
    (progn
      (setq result (vl-catch-all-apply 'vlax-invoke-method (list fso 'CopyFile path backup :vlax-false)))
      (vlax-release-object fso)
      (cond
        ((vl-catch-all-error-p result)
          (setq garari:backup-error (vl-catch-all-error-message result)) nil)
        ((not (and (setq size (vl-file-size path)) (> size 0) (= size (vl-file-size backup))))
          (setq garari:backup-error "コピー後のファイルサイズが一致しません。") nil)
        (T T)))))
(defun garari:copy-backup (path backup) (garari:copy-backup-file path backup))
;; Destination tuple: existing sheet, sheet name, owned name, rectangle, data.
;; A named rectangle is a user-assigned capacity, never an inferred UsedRange.
(defun garari:destination (sheets sheetname key data / sheet named area addr nr nc rows cols parent result areas)
  (setq sheet (vl-catch-all-apply 'vlax-get-property (list sheets 'Item sheetname))
    nr (length data) nc (length (car data)))
  (if (vl-catch-all-error-p sheet) (setq sheet nil) (setq sheet (garari:own sheet)))
  (setq named (if sheet (vl-catch-all-apply 'vlax-get-property (list sheet 'Range key))))
  (if (and named (not (vl-catch-all-error-p named)))
    (progn
      (setq area (garari:own named)
        parent (garari:own (vlax-get-property area 'Worksheet)))
      (if (/= (vla-get-Name parent) sheetname) (garari:fail "管理範囲のシートが設定と異なります。Excelの名前定義を修正してください。"))
      (setq addr (garari:address area))))
  (if (not addr)
    (if sheet
      (progn
        (princ (strcat "\n" sheetname "：管理範囲が未設定です。既存レイアウトの書込開始セルから管理する矩形を指定してください。"))
        (setq addr (getstring T (strcat "\n管理範囲（例 A5:" (garari:col nc) (itoa (+ nr 4)) "、Enterで中止）：")))
        (if (= addr "") (garari:fail "キャンセル（Excel未変更）"))
        (if (not (garari:rectangle-p addr)) (garari:fail "管理範囲はA1形式の単一矩形で指定してください。"))
        (setq result (vl-catch-all-apply 'vlax-get-property (list sheet 'Range addr)))
        (if (vl-catch-all-error-p result) (garari:fail "管理範囲が不正です。"))
        (setq area (garari:own result)))
      (setq addr (strcat "$A$1:$" (garari:col nc) "$" (itoa (max 200 nr))))))
  (if area
    (progn
      (setq areas (garari:own (vlax-get-property area 'Areas)))
      (if (/= (vlax-get-property areas 'Count) 1) (garari:fail "管理範囲は単一矩形にしてください。"))
      (garari:drop areas)
      (setq rows (garari:own (vlax-get-property area 'Rows)) cols (garari:own (vlax-get-property area 'Columns)))
      (if (or (< (vlax-get-property rows 'Count) nr) (< (vlax-get-property cols 'Count) nc))
        (garari:fail (strcat sheetname "：管理範囲が不足しています。名前定義 " key " を拡張して再実行してください。")))
      ;; Preflight rejects merges touching data on another side of the boundary.
      (garari:check-merges area)
      (if (= (vlax-get-property sheet 'ProtectContents) :vlax-true) (garari:fail "対象シートが保護されています。"))))
  (list sheet sheetname key addr data))
(defun garari:cell-p (s / i letters digits c)
  (setq i 1 letters "" digits "" s (vl-string-translate "$" " " (strcase s)) s (garari:compact s))
  (while (and (<= i (strlen s)) (>= (ascii (substr s i 1)) 65) (<= (ascii (substr s i 1)) 90))
    (setq letters (strcat letters (substr s i 1)) i (1+ i)))
  (setq digits (substr s i))
  (and (/= letters "") (<= (strlen letters) 3) (garari:digits digits) (> (atoi digits) 0) (<= (atoi digits) 1048576)))
(defun garari:rectangle-p (s / xs)
  (setq xs (garari:split s ":"))
  (and (= (length xs) 2) (garari:cell-p (car xs)) (garari:cell-p (cadr xs))))
(defun garari:check-merges (area / cells cell merged r c nr nc mr mc rr cc i seen addr indices j)
  (if (/= (vlax-get-property area 'MergeCells) :vlax-false) (progn
  (setq r (vlax-get-property area 'Row) c (vlax-get-property area 'Column)
    cells (garari:own (vlax-get-property area 'Cells))
    rr (garari:own (vlax-get-property area 'Rows)) cc (garari:own (vlax-get-property area 'Columns))
    nr (vlax-get-property rr 'Count) nc (vlax-get-property cc 'Count))
  (if (> (* nr nc) 500000) (garari:fail "管理範囲が大きすぎます（50万セル以内）。"))
  ;; Only perimeter cells can belong to a merge crossing the owned boundary.
  (setq i 1)
  (repeat nc (setq indices (cons i indices) indices (cons (+ (* (1- nr) nc) i) indices) i (1+ i)))
  (setq j 1)
  (repeat (max 0 (- nr 2))
    (setq indices (cons (1+ (* j nc)) indices) indices (cons (* (1+ j) nc) indices) j (1+ j)))
  (foreach i indices
    (setq cell (garari:own (vlax-get-property cells 'Item i)))
    (if (= (vlax-get-property cell 'MergeCells) :vlax-true)
      (progn
        (setq merged (garari:own (vlax-get-property cell 'MergeArea)) addr (garari:address merged))
        (if (not (member addr seen))
          (progn
            (setq mr (garari:own (vlax-get-property merged 'Rows)) mc (garari:own (vlax-get-property merged 'Columns)))
            (if (or (< (vlax-get-property merged 'Row) r) (< (vlax-get-property merged 'Column) c)
              (> (+ (vlax-get-property merged 'Row) (vlax-get-property mr 'Count)) (+ r nr))
              (> (+ (vlax-get-property merged 'Column) (vlax-get-property mc 'Count)) (+ c nc)))
              (garari:fail "管理範囲の境界をまたぐ結合セルがあります。範囲を修正してください。"))
            (garari:drop mr) (garari:drop mc) (setq seen (cons addr seen))))
        (garari:drop merged)))
    (garari:drop cell))
  (garari:drop rr) (garari:drop cc) (garari:drop cells))))
(defun garari:write-destination (sheets target / sheet area data row col names name missing)
  (setq garari:stage (strcat "書込 " (cadr target) " / シート"))
  (setq sheet (car target) data (nth 4 target))
  (if (not sheet) (setq sheet (garari:sheet sheets (cadr target))))
  (setq garari:stage (strcat "書込 " (cadr target) " / 範囲"))
  (setq area (garari:own (vlax-get-property sheet 'Range (nth 3 target)))
    row (vlax-get-property area 'Row) col (vlax-get-property area 'Column))
  ;; Clear only the owned rectangle. Rebuild its internal merges from the new plan.
  (vlax-invoke-method area 'UnMerge)
  (vlax-invoke-method area 'ClearContents)
  (setq garari:stage (strcat "書込 " (cadr target) " / セル"))
  (garari:put-matrix-at sheet row col data)
  (setq names (garari:own (vlax-get-property garari:book 'Names)))
  (setq garari:stage (strcat "書込 " (cadr target) " / 名前定義"))
  (setq missing (vlax-make-variant))
  (setq name (garari:own (vlax-invoke-method names 'Add (nth 2 target)
    (strcat "='" (garari:escape-sheet (cadr target)) "'!" (garari:address area))
    :vlax-true missing missing missing missing missing missing missing missing)))
  (vlax-put-property name 'RefersTo
    (strcat "='" (garari:escape-sheet (cadr target)) "'!" (garari:address area)))
  (garari:drop name) (garari:drop names) (garari:drop area))
(defun garari:merge-table (sheet address blocks nc / area r c block col merged)
  (setq area (garari:own (vlax-get-property sheet 'Range address)) r (vlax-get-property area 'Row) c (vlax-get-property area 'Column))
  (foreach block blocks
    (setq col 1)
    (repeat nc
      (if (/= col 3)
        (progn (setq merged (garari:range sheet (+ r (car block) -1) (+ c col -1) (+ r (cadr block) -1) (+ c col -1)))
          (vlax-invoke-method merged 'Merge) (garari:drop merged)))
      (setq col (1+ col))))
  (garari:drop area))
(defun garari:address (area)
  (vlax-get-property area 'Address :vlax-true :vlax-true 1 :vlax-false (vlax-make-variant)))
(defun garari:escape-sheet (s / out c)
  (setq out "") (foreach c (vl-string->list s) (setq out (strcat out (if (= c 39) "''" (chr c))))) out)

(defun c:GARARITABLE (/ *error* garari:stage garari:objects garari:excel garari:book garari:handed garari:temp garari:saved garari:file garari:reason garari:issues
  cfg master rooms masters mp records groups floors requested excluded global path settings value mode floor selection seen r warnings warning-count error-count total)
  (defun *error* (msg)
    (princ (strcat "\nGARARITABLE：" (if garari:reason garari:reason msg)))
    (if garari:stage (princ (strcat "\n処理段階：" garari:stage)))
    (garari:cleanup)
    (if garari:saved (princ "\n対象Excelの保存は完了しています。再表示に失敗したため対象ファイルを確認してください。")) (princ))
  (princ (strcat "\nGARARITABLE version " garari:version " / backup: Windows FSO"))
  (if (= (getvar "LISPSYS") 0) (garari:fail "LISPSYS=1または2に設定しAutoCADを再起動してください。"))
  (while (null requested)
    (setq value (getstring T "\n対象階（1～4 / 1,3,4 / B1F,1F,RF）："))
    (if (= (garari:trim value) "") (garari:fail "キャンセル"))
    (setq requested (garari:parse-floors value))
    (if (null requested) (princ "\n階指定が不正です。昇順の整数範囲または階名を指定してください。")))
  (initget "Select Floor") (setq mode (getkword "\n割当方式 [Select(階別選択)/Floor(FLOOR属性)] <Select>："))
  (setq cfg garari:config excluded 0)
  (initget 6) (setq value (getint "\n案件FD温度 <72>：")) (if value (setq cfg (garari:set cfg 'fd-temp (itoa value))))
  (initget 6) (setq value (getint "\n案件防虫網メッシュ数 <10>：")) (if value (setq cfg (garari:set cfg 'mesh-spec (itoa value))))
  (initget "Yes No") (setq value (getkword "\nSOUNDタグ欠落時の防音指定 [Yes/No] <No>：")) (setq cfg (garari:set cfg 'sound (if (= value "Yes") "あり" "なし")))
  (setq mp (garari:master-path) masters (garari:read-masters mp) master (car masters) rooms (cadr masters) global garari:issues)
  (foreach floor (if (= mode "Floor") '("") requested)
    (setq selection (garari:selection floor master rooms cfg records seen requested)
      records (car selection) seen (cadr selection) excluded (+ excluded (caddr selection))))
  ;; Every assigned floor is represented, including invalid/missing/out-of-scope FLOOR values.
  (setq floors requested)
  (foreach floor (garari:floors records) (if (not (member floor floors)) (setq floors (append floors (list floor)))))
  (setq records (garari:cross-check records) groups (garari:aggregate records))
  (garari:summary records groups floors excluded)
  (setq total 0)
  (foreach floor floors (foreach r records (if (= floor (garari:get r "FLOOR")) (setq total (1+ total)))))
  (if (/= total (length records)) (garari:fail "階別数量合計と採用数が一致しません"))
  (setq warnings (length global))
  (foreach r records (setq warnings (+ warnings (length (garari:get r "ISSUES")))))
  (setq warning-count (garari:issue-count records global "警告") error-count (garari:issue-count records global "エラー"))
  (setq settings (list (list "集計日時" (rtos (getvar "CDATE") 2 6))
    (list "DWG" (strcat (getvar "DWGPREFIX") (getvar "DWGNAME")))
    (list "選択方式" (if (= mode "Floor") "FLOOR属性一括" "階別選択・FLOOR優先"))
    (list "指定階" (garari:join requested "/")) (list "出力階" (garari:join floors "/"))
    (list "統合マスター" mp) (list "マスターシート" "GARARI_MASTER / ROOM_MASTER")
    (list "FD_TEMP" (cdr (assoc 'fd-temp cfg))) (list "MESH_SPEC" (cdr (assoc 'mesh-spec cfg)))
    (list "SOUND既定" (cdr (assoc 'sound cfg))) (list "除外要素" excluded)
    (list "警告・エラー件数" warnings) (list "警告件数" warning-count) (list "エラー件数" error-count)
    (list "選定範囲" "参考型番。組合せ・施工適合要確認")))
  (if (not (setq path (garari:project-book))) (garari:fail "キャンセル（対象Excel未変更）"))
  (princ (strcat "\n更新対象：" path " / " (cdr (assoc 'table-sheet garari:config)) " / 採用=" (itoa (length records)) " / 警告=" (itoa warning-count) " / エラー=" (itoa error-count)))
  (garari:write-xlsx path records groups floors settings global)
  (princ (strcat "\nGARARITABLE 更新・保存完了：" path "\nシート：" (cdr (assoc 'table-sheet garari:config))
    " / 採用=" (itoa (length records)) " / 警告=" (itoa warning-count) " / エラー=" (itoa error-count)))
  (garari:cleanup) (princ))
(princ (strcat "\nGARARITABLE loaded. Version: " garari:version " / backup: Windows FSO"))
(princ "\nCommands: GARARITABLE / GARARIMASTERSET / GARARIPROJECTSET") (princ)
