;; Full Windows AutoCAD only, disposable blank DWG. Never load in a user's DWG.
;; Set bs:log to an absolute writable path. The .scr runner invokes failure cases
;; as separate command lines so KIKISET's actual error handler runs.
(setq bs:count 0 bs:failed nil)
(defun bs:log-line (message / file)
  (setq file (open bs:log "a" "utf8")) (write-line message file) (close file) (princ message))
(defun bs:assert (ok label)
  (if ok (progn (setq bs:count (1+ bs:count)) (bs:log-line (strcat "\nPASS: " label)))
    (progn (setq bs:failed T) (bs:log-line (strcat "\nFAIL: " label)) (exit))))
(defun bs:snapshot (handle / block attrs attr result)
  (setq block (vlax-ename->vla-object (handent handle)) attrs (ks:get-attributes block))
  (foreach attr attrs
    (setq result (cons (list (vla-get-TagString attr) (vla-get-TextString attr) (vla-get-Invisible attr)) result))
    (ks:release attr))
  (ks:release block) result)
(defun bs:model (handle) (cadr (assoc "MODEL" (bs:snapshot handle))))
(bs:assert (not (tblsearch "BLOCK" "KANKI_KIKI")) "blank-drawing-guard")
(setq bs:doc (vla-get-ActiveDocument (vlax-get-acad-object)))
(bs:assert bs:doc "full-autocad-active-document")
(setq bs:defs (vla-get-Blocks bs:doc) bs:space (vla-get-ModelSpace bs:doc)
  bs:layers (vla-get-Layers bs:doc) bs:locked (vla-Add bs:layers "KIKI_BATCH_LOCK"))
(foreach bs:name '("KANKI_KIKI" "KUCHO_KIKI" "BATCH_PLAIN")
  (setq bs:def (vla-Add bs:defs (vlax-3d-point '(0.0 0.0 0.0)) bs:name))
  (if (/= bs:name "BATCH_PLAIN")
    (foreach bs:tag (append ks:protected '("MODEL" "MAKER" "CUSTOM"))
      (setq bs:attr (vla-AddAttribute bs:def 2.5 (if (= bs:tag "MODEL") 0 1)
        bs:tag (vlax-3d-point '(0.0 0.0 0.0)) bs:tag "OLD"))
      (ks:release bs:attr)))
  (ks:release bs:def))
(setq bs:ss (ssadd) bs:index 0)
(foreach bs:name '("KANKI_KIKI" "KANKI_KIKI" "KUCHO_KIKI" "KANKI_KIKI" "BATCH_PLAIN")
  (setq bs:index (1+ bs:index)
    bs:block (vla-InsertBlock bs:space (vlax-3d-point (list (* 100.0 bs:index) 0.0 0.0)) bs:name 1.0 1.0 1.0 0.0))
  (if (= bs:index 4) (vla-put-Layer bs:block "KIKI_BATCH_LOCK"))
  (if (/= bs:name "BATCH_PLAIN")
    (foreach bs:attr (ks:get-attributes bs:block)
      (vla-put-TextString bs:attr (strcat "ORIGINAL-" (itoa bs:index) "-" (vla-get-TagString bs:attr)))
      (ks:release bs:attr)))
  (setq bs:handles (append bs:handles (list (vla-get-Handle bs:block))))
  (ssadd (vlax-vla-object->ename bs:block) bs:ss) (ks:release bs:block))
(vla-put-Lock bs:locked :vlax-true)
(foreach bs:o (list bs:locked bs:layers bs:space bs:defs bs:doc) (ks:release bs:o))
(setq bs:before (mapcar 'bs:snapshot (list (nth 0 bs:handles) (nth 1 bs:handles))))
(setq bs:filtered (ks:filter-blocks bs:ss "KANKI_KIKI"))
(bs:assert (= (length bs:filtered) 2) "category-locked-and-attribute-filter")
(foreach bs:o bs:filtered (ks:release bs:o))
;; Only user input and master acquisition are supplied by the fixture.
(defun ks:category () "KANKI")
(defun ks:select-blocks (name) (ks:filter-blocks bs:ss name))
(defun ks:file () "fixture-only")
(defun ks:load-master (path sheet) (setq bs:loads (1+ bs:loads)) (list (cons 3 (list (cons "MODEL" bs:selected-model) '("MAKER" . "BATCH-MAKER")))))
(defun ks:select-record (records) (setq bs:choices (1+ bs:choices)) (if bs:cancel nil (car records)))
(setq bs:loads 0 bs:choices 0 bs:selected-model "BATCH-MODEL")
(c:KIKISET)
(bs:assert (and (= bs:loads 1) (= bs:choices 1)) "one-master-load-and-one-model-choice")
(setq bs:index 0)
(foreach bs:handle (list (nth 0 bs:handles) (nth 1 bs:handles))
  (setq bs:after (bs:snapshot bs:handle))
  (bs:assert (= (cadr (assoc "MODEL" bs:after)) "BATCH-MODEL") "model-updated-on-both-blocks")
  (foreach bs:tag (append ks:protected '("CUSTOM"))
    (bs:assert (equal (assoc bs:tag bs:after) (assoc bs:tag (nth bs:index bs:before))) (strcat "protected-and-visibility-" bs:tag)))
  (setq bs:index (1+ bs:index)))
(bs:assert (= (bs:model (nth 2 bs:handles)) "ORIGINAL-3-MODEL") "other-category-unchanged")
(bs:assert (= (bs:model (nth 3 bs:handles)) "ORIGINAL-4-MODEL") "locked-block-unchanged")
(setq bs:baseline (mapcar 'bs:snapshot (list (nth 0 bs:handles) (nth 1 bs:handles))))
(defun bs:inject-failure ()
  (setq bs:selected-model "MUST-ROLL-BACK" bs:normal-update ks:update-batches)
  (defun ks:update-batches (batches data / batch)
    (foreach batch batches (ks:update (cadr batch) data))
    (ks:fail "Injected failure after changing both blocks")))
(defun bs:verify-rollback ()
  (bs:assert (equal bs:baseline (mapcar 'bs:snapshot (list (nth 0 bs:handles) (nth 1 bs:handles)))) "failure-restores-both-blocks-and-visibility")
  (setq ks:update-batches bs:normal-update bs:cancel T))
(defun bs:finish ()
  (bs:assert (equal bs:baseline (mapcar 'bs:snapshot (list (nth 0 bs:handles) (nth 1 bs:handles)))) "cancel-before-update-leaves-both-unchanged")
  (if (not bs:failed) (bs:log-line (strcat "\nKIKISET_BATCH_PASS=" (itoa bs:count)))))
