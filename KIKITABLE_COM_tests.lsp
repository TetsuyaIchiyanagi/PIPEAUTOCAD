;; KIKITABLE.lsp と KIKITABLE_tests.lsp をロードして KIKITABLECOMTEST。
;; 一時フォルダに専用xlsxを生成する。実案件のExcel・図面には触れない。
(defun ktt:locked-p (path / kt:objects kt:excel kt:book kt:reason result)
  ;; 呼出し元のExcel所有権を局所変数で分離して二重更新防止を確認する。
  (setq result (vl-catch-all-apply 'kt:open (list path)))
  (kt:cleanup)
  (and (vl-catch-all-error-p result) kt:reason))
(defun ktt:fixture (/ books sheets ws other area font borders setup col text)
  (setq kt:stage "fixture Excel creation")
  (setq kt:excel (vlax-create-object "Excel.Application"))
  (vlax-put-property kt:excel 'Visible :vlax-false)
  (vlax-put-property kt:excel 'DisplayAlerts :vlax-false)
  (setq books (kt:own (vlax-get-property kt:excel 'Workbooks))
        kt:book (kt:own (vlax-invoke-method books 'Add))
        sheets (kt:own (vlax-get-property kt:book 'Worksheets))
        ws (kt:own (vlax-get-property sheets 'Item 1)))
  (vlax-put-property ws 'Name (kt:cfg 'sheet))
  (setq kt:stage "fixture headers")
  (setq col 2)
  (foreach text '("記号" "名称" "参考型番" "機器仕様" "場所" "φ" "V" "kW" "1F" "2F" "数量" "備考")
    (kt:put ws 5 col text) (setq col (1+ col)))
  (setq area (kt:range ws 6 2 12 13)
        font (kt:own (vlax-get-property area 'Font))
        borders (kt:own (vlax-get-property area 'Borders)))
  (vlax-put-property font 'Name "ＭＳ ゴシック")
  (vlax-put-property font 'Size 9)
  (vlax-put-property borders 'LineStyle 1)
  (vlax-put-property area 'RowHeight 22)
  (vlax-put-property area 'WrapText :vlax-true)
  (kt:drop borders) (kt:drop font) (kt:drop area)
  (foreach col '(2 3 7 8 9)
    (setq kt:stage "fixture merge")
    (setq area (kt:range ws 6 col 11 col))
    (vlax-invoke-method area 'Merge :vlax-false) (kt:drop area))
  (setq kt:stage "fixture page setup")
  (setq setup (kt:own (vlax-get-property ws 'PageSetup)))
  (vlax-put-property setup 'PrintArea "$A$1:$M$12")
  (kt:drop setup)
  (setq other (kt:own (vlax-invoke-method sheets 'Add)))
  (vlax-put-property other 'Name "KEEP")
  (kt:put other 1 1 "untouched")
  ws)
(defun c:KIKITABLECOMTEST (/ *error* kt:objects kt:excel kt:book kt:reason kt:stage
                           kt:cell-context kt:warnings kt:raw-tags kt:plan ktt:passed
                           path records groups sheets ws raw other area font setup result)
  (defun *error* (msg)
    (princ (strcat "\nKIKITABLECOMTEST FAILED [" (if kt:stage kt:stage "start") "]: " (if kt:reason kt:reason msg)))
    (kt:cleanup) (princ))
  (setq ktt:passed 0 kt:raw-tags (append (kt:raw-columns) '("NOTE")))
  (setq path (vl-filename-mktemp "kikitable-test-" nil ".xlsx"))
  (ktt:fixture)
  (setq kt:stage "fixture SaveAs")
  (princ "\nCOM test: SaveAs")
  (vlax-invoke-method kt:book 'SaveAs path 51 "" "" :vlax-false :vlax-false 1 2 :vlax-false 65001 1 :vlax-false)
  (ktt:assert (ktt:locked-p path) "Reject already open target workbook")
  (setq sheets (kt:own (vlax-get-property kt:book 'Worksheets)) other (kt:sheet sheets "KEEP"))
  (ktt:assert (= (kt:cell-value other 1 1) "untouched") "Keep original Excel instance open")
  (kt:cleanup)
  (princ "\nCOM test: fixture saved")
  (setq records (list (ktt:record "PAC-7" "職員室" "2" "備考")
                      (ktt:record "PAC-7" "会議室" "1" "備考")
                      (ktt:record "PAC-7" "職員室" "2" "備考")
                      (ktt:record "PAC-2" "室2" "1" "")
                      (ktt:record "PAC-10" "室10" "2" "")))
  (setq kt:stage "first open") (kt:open path)
  (kt:write-book records (kt:group records))
  (princ "\nCOM test: first write completed")
  (vlax-invoke-method kt:book 'Save)
  (kt:cleanup)
  ;; 保存後に開き直して確認する。
  (kt:open path)
  (setq sheets (kt:own (vlax-get-property kt:book 'Worksheets))
        ws (kt:sheet sheets (kt:cfg 'sheet)) raw (kt:sheet sheets (kt:cfg 'raw-sheet))
        other (kt:sheet sheets "KEEP"))
  (ktt:assert (= (kt:cell-value ws 6 2) "PAC-2") "Saved natural order first")
  (ktt:assert (= (kt:cell-value ws 13 2) "PAC-7") "Saved natural order second")
  (ktt:assert (= (kt:cell-value ws 20 2) "PAC-10") "Copied third equipment frame")
  (ktt:assert (= (kt:cell-value ws 13 6) "職員室(2)") "Saved grouped location")
  (ktt:assert (= (kt:cell-value ws 13 11) 2.0) "Saved floor count numeric")
  (ktt:assert (= (kt:cell-value ws 14 12) 3.0) "Saved total at final row")
  (ktt:assert (equal (kt:cell-value ws 13 9) 2.22 1e-10) "Saved max power")
  (ktt:assert (= (kt:cell-value ws 17 5) "圧縮機出力2.10kW　室内送風機出力0.120kW　室外送風機出力0.060kW×2") "Saved Japanese specification")
  (ktt:assert (= (kt:cell-value raw 1 1) "SYSTEM") "Raw headers")
  (ktt:assert (= (kt:cell-value raw 6 3) "PAC-10") "Every block and derived key in raw")
  (ktt:assert (= (kt:cell-value raw 6 2) "10") "Raw number retained")
  (ktt:assert (= (kt:cell-value ws 13 3) (kt:cfg 'equipment-name)) "Saved configured equipment name")
  (ktt:assert (= (kt:cell-value ws 13 7) "3") "Saved phase without phi")
  (ktt:assert (= (kt:cell-value ws 18 5) "ワイヤードリモコン、その他付属品一式") "Saved remote sentence")
  (ktt:assert (= (kt:cell-value raw 2 (1+ (vl-position "FREQ" kt:raw-tags))) "50") "Raw frequency")
  (ktt:assert (= (kt:cell-value raw 2 (1+ (vl-position "GAS_PIPE" kt:raw-tags))) "15.88") "Raw gas pipe")
  (ktt:assert (= (kt:cell-value raw 2 (1+ (vl-position "LIQ_PIPE" kt:raw-tags))) "9.52") "Raw liquid pipe")
  (ktt:assert (= (kt:cell-value other 1 1) "untouched") "Other sheet preserved")
  (setq area (kt:range ws 13 2 13 2) font (kt:own (vlax-get-property area 'Font)))
  (ktt:assert (= (kt:unwrap (vlax-get-property font 'Size)) 9.0) "Copied font size")
  (ktt:assert (= (kt:unwrap (vlax-get-property area 'RowHeight)) 22.0) "Copied row height")
  (ktt:assert (= (kt:unwrap (vlax-get-property area 'MergeCells)) :vlax-true) "Copied merged cell")
  (kt:drop font) (kt:drop area)
  (setq setup (kt:own (vlax-get-property ws 'PageSetup)))
  (ktt:assert (= (vlax-get-property setup 'PrintArea) "$A$1:$M$26") "Print area extended")
  (kt:drop setup)
  ;; 再実行で件数を減らし、旧データが帳票にもCAD_DATAにも残らないこと。
  (setq records (list (ktt:record "PAC-7" "新しい場所" "2" "=literal")))
  (kt:write-book records (kt:group records))
  (vlax-invoke-method kt:book 'Save)
  (kt:cleanup)
  (kt:open path)
  (setq sheets (kt:own (vlax-get-property kt:book 'Worksheets))
        ws (kt:sheet sheets (kt:cfg 'sheet)) raw (kt:sheet sheets (kt:cfg 'raw-sheet)))
  (ktt:assert (= (kt:cell-value ws 6 2) "PAC-7") "Rerun new first entry")
  (ktt:assert (null (kt:cell-value ws 13 2)) "Rerun removes old second entry")
  (ktt:assert (null (kt:cell-value ws 20 2)) "Rerun removes old third entry")
  (ktt:assert (null (kt:cell-value raw 3 1)) "Rerun removes stale raw data")
  (ktt:assert (= (kt:cell-value ws 6 13) "=literal") "Text is not a formula")
  ;; 保護シートへの書込み失敗では、未保存の編集を残さない。
  (vlax-invoke-method ws 'Protect "test")
  (setq result (vl-catch-all-apply 'kt:write-book (list records (kt:group records))))
  (ktt:assert (vl-catch-all-error-p result) "Protected sheet stops update")
  (kt:cleanup)
  (kt:open path)
  (setq sheets (kt:own (vlax-get-property kt:book 'Worksheets)) ws (kt:sheet sheets (kt:cfg 'sheet)))
  (ktt:assert (= (kt:cell-value ws 6 6) "新しい場所") "Failed update did not save")
  (ktt:assert (= (kt:unwrap (vlax-get-property ws 'ProtectContents)) :vlax-false) "Unsaved protection discarded")
  (kt:cleanup)
  (ktt:assert (and (null kt:objects) (null kt:book) (null kt:excel)) "COM references cleared")
  (princ (strcat "\nKIKITABLECOMTEST PASSED: " (itoa ktt:passed) "\nTest workbook: " path))
  (princ))
