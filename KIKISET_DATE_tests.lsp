;; 10_kikiset.lsp と KIKISET_MASTER_tests.lsp の後にロードする。
(defun c:KIKISETDATETEST (/ kst:count records ks:date1904 ks:stage record ks:category-id)
  (setq kst:count 0)
  (kst:assert (= (ks:registration-day "2026-09-28") (ks:registration-day "2026/09/28")) "Date formats")
  (kst:assert (= (ks:registration-day "25569") (ks:day-number 1970 1 1)) "Excel epoch")
  (kst:assert (= (ks:registration-day "25569.75") (ks:day-number 1970 1 1)) "Ignore time")
  (kst:assert (null (ks:registration-day "2026-02-29")) "Invalid leap date")
  (kst:assert (ks:registration-day "2024-02-29") "Valid leap date")
  (kst:assert (null (ks:registration-day "")) "Blank date")
  (kst:assert (null (ks:registration-day "today")) "Invalid text")
  (setq records '((3 ("MODEL" . "A") ("REGISTERED_DATE" . "2026-09-28"))
                  (4 ("MODEL" . "A") ("REGISTERED_DATE" . "2026-09-28"))
                  (5 ("MODEL" . "B") ("REGISTERED_DATE" . "2026-09-27"))
                  (6 ("MODEL" . "C"))))
  (kst:assert (= (length (ks:registered-on records (ks:day-number 2026 9 28))) 2) "Keep duplicate model rows")
  (kst:assert (null (ks:registered-on records (ks:day-number 2026 9 29))) "No matches")
  (setq ks:date1904 T record (ks:make-record 3 '(24107 "A") '(("REGISTERED_DATE" . 0) ("MODEL" . 1))))
  (kst:assert (= (ks:record-value record "REGISTERED_DATE") "25569") "1904 system conversion")
  (kst:assert (not (assoc "REGISTERED_DATE" (ks:record-data record))) "Date metadata not written")
  (kst:assert (numberp (ks:today)) "Local calendar date")
  ;; 換気でも登録日を保持して絞り込み、転記時だけ仕様属性に限定する。
  (setq ks:category-id "KANKI" ks:date1904 nil
        record (ks:make-record 3 '("VD-10ZVC7" "2026-09-28" "100")
          '(("MODEL" . 0) ("REGISTERED_DATE" . 1) ("AIRFLOW" . 2)) ))
  (kst:assert (= (caddr (assoc "KANKI" ks:profiles)) "KANKI_MASTER") "Vent sheet")
  (kst:assert (equal (ks:registered-on (list record) (ks:day-number 2026 9 28)) (list record)) "Vent today candidate")
  (kst:assert (= (ks:row-label record) "VD-10ZVC7") "Vent model only label")
  (kst:assert (not (assoc "REGISTERED_DATE" (ks:record-data record))) "Vent date not written")
  (kst:assert (= (cdr (assoc "AIRFLOW" (ks:record-data record))) "100") "Vent specifications retained")
  (princ (strcat "\nKIKISETDATETEST PASSED: " (itoa kst:count))) (princ))
