;; 新規の作業用図面だけで実行する。試験後も未使用のブロック定義は残る。
;; KIKITABLE.lsp、KIKITABLE_tests.lspを先にロードする。
(defun ktt:make-insert (name key place floor / entity pair split)
  (setq split (vl-string-search "-" key))
  (entmake (list '(0 . "INSERT") (cons 2 name) '(66 . 1) '(10 0.0 0.0 0.0)))
  (foreach pair (list (cons "SYSTEM" (substr key 1 split)) (cons "NUM" (substr key (+ split 2))) (cons "LOCATION" place)
                      (cons "FLOOR" floor) '("MODEL" . "TEST-MODEL"))
    (entmake (list '(0 . "ATTRIB") '(10 0.0 0.0 0.0) '(40 . 2.5)
                   (cons 1 (cdr pair)) (cons 2 (car pair)) '(70 . 0))))
  (entmake '((0 . "SEQEND"))) (entlast))
(defun c:KIKITABLECADTEST (/ *error* kt:config kt:objects kt:warnings kt:raw-tags
                           kt:reason ktt:passed entities entity tag records name)
  (defun *error* (msg)
    (foreach entity entities (if entity (entdel entity)))
    (kt:cleanup) (princ (strcat "\nKIKITABLECADTEST FAILED: " msg)) (princ))
  (setq name "KIKITABLE_TEST_BLOCK" ktt:passed 0)
  (if (tblsearch "BLOCK" name) (progn (princ "\n新しい作業用図面で実行してください。") (exit)))
  ;; 設定を局所的に差し替え、実案件のKUCHO_KIKIは収集しない。
  (setq kt:config (list (cons 'block name)) kt:raw-tags (kt:raw-columns))
  (entmake (list '(0 . "BLOCK") (cons 2 name) '(70 . 2) '(10 0.0 0.0 0.0)))
  (foreach tag '("SYSTEM" "NUM" "LOCATION" "FLOOR" "MODEL")
    (entmake (list '(0 . "ATTDEF") '(10 0.0 0.0 0.0) '(40 . 2.5)
                   '(1 . "") (cons 2 tag) (cons 3 tag) '(70 . 0))))
  (entmake '((0 . "ATTDEF") (10 0.0 0.0 0.0) (40 . 2.5)
             (1 . "固定メーカー") (2 . "MAKER") (3 . "MAKER") (70 . 2)))
  (entmake '((0 . "ENDBLK")))
  (setq entities (list (ktt:make-insert name "PAC-7" "職員室" "2")
                       (ktt:make-insert name "PAC-7" "会議室" "1")
                       (ktt:make-insert name "PAC-2" "室2" "1")))
  (setq records (kt:collect))
  (ktt:assert (= (length records) 3) "Collect all placed blocks")
  (ktt:assert (= (length (kt:group records)) 2) "Group collected blocks")
  (ktt:assert (= (kt:get (car records) "MODEL") "TEST-MODEL") "Read editable attributes")
  (ktt:assert (= (kt:get (car records) "MAKER") "固定メーカー") "Read constant attributes")
  (ktt:assert (null kt:warnings) "Optional missing tags allowed")
  (ktt:assert (/= (kt:get (car records) "KIKI_NO") "") "Derive key without CAD attribute")
  (foreach entity entities (if entity (entdel entity)))
  (kt:cleanup)
  (princ (strcat "\nKIKITABLECADTEST PASSED: " (itoa ktt:passed))) (princ))
