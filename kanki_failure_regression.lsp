;; Every case is opened from the same pristine COPY and closed without Save.
(defun kr:catch-write ()
  (setq kt:reason nil kt:stage "回帰テスト")
  (vl-catch-all-apply 'kt:write-book (list (list kr:a) (kt:group (list kr:a)))))
(defun kr:expected (result pattern label)
  (kr:assert (and (vl-catch-all-error-p result) kt:reason (wcmatch kt:reason pattern)) label))
(defun kr:reset-failure ()
  (kt:open kr:failure-fixture)
  (setq kr:sheets (kt:own (vlax-get-property kt:book 'Worksheets)) kr:ws (kt:sheet kr:sheets kc:sheet-name)))
(defun kr:blank-calc ()
  (vlax-invoke-method kr:ws 'Delete)
  (setq kr:ws nil)
  (kc:write (list kr:a))
  (setq kr:ws kc:verify-sheet))
(kr:reset-failure)
(setq kr:attempt (kr:catch-write))
(kr:expected kr:attempt "*Excelエラー*" "existing-ref-error-aborts") (kt:cleanup)
(kr:reset-failure)
(vlax-invoke-method kr:ws 'Delete)
(setq kr:template (getenv "PIPEAUTOCAD_KANKI_TEMPLATE"))
(setenv "PIPEAUTOCAD_KANKI_TEMPLATE" "C:/nonexistent-kanki-template.xlsx")
(setq kr:attempt (kr:catch-write))
(setenv "PIPEAUTOCAD_KANKI_TEMPLATE" kr:template)
(kr:expected kr:attempt "*テンプレートがありません*" "missing-template-aborts") (kt:cleanup)
(kr:reset-failure) (kr:blank-calc)
(setq kr:machine (kt:sheet kr:sheets "機器表 (換気設備)"))
(vlax-invoke-method kr:machine 'Protect "test")
(setq kr:attempt (kr:catch-write))
(kr:assert (and (vl-catch-all-error-p kr:attempt) (= kt:stage "換気表の可変行・書式展開")) "write-error-after-calc-aborts-transaction") (kt:cleanup)
(kr:reset-failure) (kr:blank-calc)
(vlax-invoke-method kr:ws 'Protect "test")
(kr:expected (kr:catch-write) "*保護されています*" "protected-calculation-aborts") (kt:cleanup)
(kr:reset-failure) (kr:blank-calc)
(setq kr:cell (kt:range kr:ws 6 3 6 4))
(vlax-invoke-method kr:cell 'Merge) (kt:drop kr:cell)
(kr:expected (kr:catch-write) "*未対応の結合*" "unsupported-merge-aborts") (kt:cleanup)
(kr:reset-failure) (kr:blank-calc)
(kt:put-matrix kr:ws 7 3 '(("1F" "事務室")))
(kr:expected (kr:catch-write) "*部屋キー重複*" "duplicate-room-aborts") (kt:cleanup)
(kr:reset-failure) (kr:blank-calc)
(kt:put kr:ws 3 5 "wrong")
(kr:expected (kr:catch-write) "*見出し不一致*" "header-mismatch-aborts") (kt:cleanup)
(kr:reset-failure) (kr:blank-calc)
(setq kr:dependent (kt:own (vlax-invoke-method kr:sheets 'Add)))
(setq kr:cell (kt:range kr:dependent 1 1 1 1))
(vlax-put-property kr:cell 'Formula "=IF('CAD_DATA_KANKI'!A2=\"EF\",1/0,1)") (kt:drop kr:cell)
(kr:expected (kr:catch-write) "*新しいExcelエラー*" "new-dependent-formula-error-aborts") (kt:cleanup)
(kr:assert (= (car (kc:capacity (list (subst '("AIRFLOW" . "0") (assoc "AIRFLOW" kr:a) kr:a)) kr:uses)) "") "zero-airflow-excluded")
(setq kr:supply (subst '("SYSTEM" . "SF") (assoc "SYSTEM" kr:b) kr:b)
  kr:mixeduses (append kr:uses '((("SF" "3" "TEST-430") "給気" "単室"))))
(kr:assert (= (car (kc:capacity (list kr:a kr:supply) kr:mixeduses)) "") "supply-exhaust-not-summed")
(kr:assert (= (car (kc:capacity (list kr:a) '((("EF" "3" "TEST-430") "排気" "複数室")))) "") "multiroom-excluded")
(kr:reset-failure)
(setq kt:config kt:aircon-config kt:tags kt:aircon-tags kt:raw-tags (kt:raw-columns)
  kr:air '(("SYSTEM" . "PAC") ("NUM" . "1") ("MODEL" . "AIR-TEST") ("LOCATION" . "空調試験室")
    ("FLOOR" . "1") ("COOL_POWER" . "1") ("HEAT_POWER" . "2")))
(kt:write-book (list kr:air) (kt:group (list kr:air)))
(setq kr:airws (kt:sheet kr:sheets "機器表 (空調設備)"))
(kr:assert (= (kt:cell-value kr:airws 6 2) "PAC-1") "existing-aircon-symbol-output")
(kr:assert (= (kt:cell-value kr:airws 6 9) 2.0) "existing-aircon-max-power")
(kr:assert (= (kt:cell-value kr:ws 6 4) "書庫（和室）") "aircon-does-not-write-calc")
(kt:cleanup)
(setq kt:config (append kt:vent-config kt:aircon-config) kt:tags kt:vent-tags)
(kr:assert (= (length (kt:vent-spec (subst '("EQUIP_TYPE" . "全熱交換器") (assoc "EQUIP_TYPE" kr:a) kr:a))) 3) "existing-heat-exchanger-three-spec-lines")
;; Existing reference layout, repaired only in this unsaved test copy.
(kr:reset-failure)
(kt:clear kr:ws 6 9 7 9)
(setq kr:left (vlax-get-property (setq kr:cell (kt:range kr:ws 6 1 25 2)) 'Formula)) (kt:drop kr:cell)
(setq kr:right (vlax-get-property (setq kr:cell (kt:range kr:ws 6 23 25 24)) 'Formula)) (kt:drop kr:cell)
(setq kr:bottom (vlax-get-property (setq kr:cell (kt:range kr:ws 26 1 26 24)) 'Formula)) (kt:drop kr:cell)
(setq kr:attempt (kr:catch-write))
(kr:expected kr:attempt "*新しいExcelエラー*" "reference-helper-new-error-aborts")
(princ (strcat "\nREFERENCE_COMPATIBILITY: " kt:reason))
(setq kr:ws kc:verify-sheet)
(kr:assert (= (kt:cell-value kr:ws 6 8) 6.0) "existing-reference-room-input-preserved")
(setq kr:cell (kt:range kr:ws 6 1 25 2))
(kr:assert (equal (kt:array kr:left) (kt:array (vlax-get-property kr:cell 'Formula))) "existing-reference-left-unchanged") (kt:drop kr:cell)
(setq kr:cell (kt:range kr:ws 6 23 25 24))
(kr:assert (equal (kt:array kr:right) (kt:array (vlax-get-property kr:cell 'Formula))) "existing-reference-right-unchanged") (kt:drop kr:cell)
(setq kr:cell (kt:range kr:ws 26 1 26 24))
(kr:assert (equal (kt:array kr:bottom) (kt:array (vlax-get-property kr:cell 'Formula))) "existing-reference-row26-unchanged") (kt:drop kr:cell)
(kt:cleanup)
(princ (strcat "\nKANKI_FAILURE_PASS_TOTAL=" (itoa kr:count))) (princ)
