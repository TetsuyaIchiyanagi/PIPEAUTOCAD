;; Run in an isolated AutoCAD Core Console; never operate on the user's drawing.
(setq gt:count 0)
(defun gt:assert (condition label)
  (if (not condition) (progn (princ (strcat "\nFAIL: " label)) (exit)))
  (setq gt:count (1+ gt:count)) (princ (strcat "\nPASS: " label)))
(defun gt:raw (room dia)
  (list '("GARARI" . "01") (cons "DIA" dia) '("FD" . "あり") '("SHAPE" . "深型")
    '("MATERIAL" . "SUS") '("MESH" . "あり") (cons "ROOM" room)))
(setq gt:trace '(("HANDLE" . "A1") ("DWG" . "test.dwg") ("NAME" . "GARARI") ("LAYER" . "0") ("POINT" 0.0 0.0 0.0) ("SELECT_FLOOR" . "1F") ("FLOOR" . "1F") ("ISSUES")))
(gt:assert (equal (garari:parse-floors "1～4") '("1F" "2F" "3F" "4F")) "range-wave")
(gt:assert (equal (garari:parse-floors "１ － ４") '("1F" "2F" "3F" "4F")) "fullwidth-space-range")
(gt:assert (equal (garari:parse-floors "1,3,4,1F") '("1F" "3F" "4F")) "list-dedup")
(gt:assert (equal (garari:parse-floors "B１F，1F，RF") '("B1F" "1F" "RF")) "basement-roof")
(foreach v '("4-1" "1--4" "B1F-3F" "0-2" "1," "1-1000" "X" "" "1F,0F") (gt:assert (null (garari:parse-floors v)) (strcat "reject-" v)))
(gt:assert (= (garari:floor-name " ０１ｆ ") "1F") "floor-canonical")
(setq gt:masters (garari:read-masters (garari:master-path)) gt:out (car gt:masters) gt:rooms (cadr gt:masters))
(gt:assert (= (length gt:rooms) 2) "master-read-two-room-products")
(foreach v '("あり" "有" "有り" "YES" "Y" "1")
  (setq gt:r (garari:record (gt:raw v "100") gt:trace gt:out gt:rooms garari:config))
  (gt:assert (= (garari:room-model gt:r) "P-13WQU") (strcat "room-100-" v)))
(setq gt:r150 (garari:record (gt:raw "あり" "150") gt:trace gt:out gt:rooms garari:config))
(gt:assert (= (garari:room-model gt:r150) "P-18WQU") "room-150")
(gt:assert (= (garari:get (garari:get gt:r150 "OUTDOOR") "MODEL") "P-18VSQD4") "outdoor-unchanged")
(foreach v '("なし" "無" "無し" "NO" "N" "0")
  (setq gt:r (garari:record (gt:raw v "100") gt:trace gt:out gt:rooms garari:config))
  (gt:assert (and (= (garari:room-model gt:r) "") (null (garari:get gt:r "INDOOR"))) (strcat "room-none-" v)))
(setq gt:r (garari:record (gt:raw "" "100") gt:trace gt:out gt:rooms garari:config))
(gt:assert (= (garari:state gt:r) "エラー") "blank-room-error")
(setq gt:r (garari:record (vl-remove-if '(lambda (x) (= (car x) "ROOM")) (gt:raw "あり" "100")) gt:trace gt:out gt:rooms garari:config))
(gt:assert (= (garari:state gt:r) "エラー") "missing-room-error")
(setq gt:r (garari:record (gt:raw "あり" "200") gt:trace gt:out gt:rooms garari:config))
(gt:assert (= (garari:room-model gt:r) "要選定") "unregistered-no-approximation")
(setq gt:r (garari:record (gt:raw "あり" "100") gt:trace gt:out (append gt:rooms (list (car gt:rooms))) garari:config))
(gt:assert (and (null (garari:get gt:r "INDOOR")) (= (garari:state gt:r) "エラー")) "room-default-conflict")
(setq gt:r (garari:record (gt:raw "あり" "100") gt:trace gt:out (list (garari:set (car gt:rooms) "AUTO_SELECT" "0")) garari:config))
(gt:assert (null (garari:get gt:r "INDOOR")) "disabled-auto")
(setq gt:r (garari:record (gt:raw "あり" "100") gt:trace gt:out (list (garari:set (car gt:rooms) "APPROVED" "0")) garari:config))
(gt:assert (null (garari:get gt:r "INDOOR")) "unapproved")
(setq gt:r (garari:record (gt:raw "あり" "100") gt:trace gt:out (list (garari:set (car gt:rooms) "MANUFACTURER" "other")) garari:config))
(gt:assert (null (garari:get gt:r "INDOOR")) "manufacturer-filter")
(setq gt:r (garari:record (gt:raw "p-13wqu" "100") gt:trace gt:out gt:rooms garari:config))
(gt:assert (and (= (garari:room-model gt:r) "P-13WQU") (vl-string-search "旧ROOM" (garari:notes (list gt:r)))) "legacy-read-warning")
(setq gt:r (garari:record (gt:raw "P-13WQU" "150") gt:trace gt:out gt:rooms garari:config))
(gt:assert (and (= (garari:room-model gt:r) "P-13WQU") (null (garari:get gt:r "INDOOR")) (= (garari:state gt:r) "エラー")) "legacy-dia-mismatch-preserved")
(setq gt:r (garari:record (append (gt:raw "あり" "100") '(("FLOOR" . "２Ｆ"))) gt:trace gt:out gt:rooms garari:config))
(gt:assert (= (garari:get gt:r "FLOOR") "2F") "floor-priority")
(setq gt:plan (garari:table-plan (garari:aggregate (list gt:r150)) '("1F" "2F" "3F" "4F")))
(gt:assert (equal (nth 4 (car (car gt:plan))) "1F") "requested-columns")
(gt:assert (equal (list (nth 4 (cadr (car gt:plan))) (nth 5 (cadr (car gt:plan))) (nth 8 (cadr (car gt:plan)))) '(1 0 1)) "floor-zero-single-set")
(gt:assert (vl-string-search "P-18WQU" (nth 2 (nth 3 (car gt:plan)))) "table-auto-room")
(setq gt:data (garari:raw-data (list gt:r150)))
(gt:assert (= (nth 11 (cadr gt:data)) "P-18WQU") "cad-data-auto-room")
(gt:assert (= (length (car gt:data)) (length (cadr gt:data))) "cad-data-width")
(foreach v '("A5:J100" "$B$5:$K$200") (gt:assert (garari:rectangle-p v) (strcat "rectangle-" v)))
(foreach v '("A1" "A1:J2,K1:K2" "A:A" "Sheet1!A1:J2" "A0:J5") (gt:assert (null (garari:rectangle-p v)) (strcat "bad-rectangle-" v)))
(gt:assert (= (garari:spec-note "フラットカバー付BSW-SB初期案") "フラットカバー付BSW-SB") "spec-omit-master-draft-label")
(gt:assert (= (garari:spec-note "施工適合要確認") "施工適合要確認") "spec-preserve-technical-note")
(setq gt:issues '((("ISSUES" ("警告" "ROOM" "check") ("エラー" "DIA" "invalid"))) (("ISSUES" ("警告" "FLOOR" "check")))))
(gt:assert (= (garari:issue-count gt:issues '(("警告" "MASTER" "check")) "警告") 3) "count-record-and-global-warnings")
(gt:assert (= (garari:issue-count gt:issues '(("警告" "MASTER" "check")) "エラー") 1) "count-errors-separately")
(gt:assert (= (garari:issue-count nil nil "エラー") 0) "count-no-issues")
(setq gt:compact-record (garari:record (garari:set (gt:raw "なし" "100") "GARARI" "a") gt:trace gt:out gt:rooms garari:config))
(setq gt:compact-plan (garari:table-plan (garari:aggregate (list gt:r150 gt:compact-record)) '("1F")))
(gt:assert (= (length (car gt:compact-plan)) 6) "table-two-items-no-spacer-or-trailing-row")
(gt:assert (= (car (cadr (cadr gt:compact-plan))) (1+ (cadr (car (cadr gt:compact-plan))))) "table-item-blocks-contiguous")
(princ (strcat "\nGARARI_REGRESSION_OK=" (itoa gt:count)))
(princ)
