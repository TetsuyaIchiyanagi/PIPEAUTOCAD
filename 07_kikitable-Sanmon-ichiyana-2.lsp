;; KIKITABLE — 図面属性から案件Excelの空調機器表を更新する単体モジュール。
;; Windows AutoCAD / Excel COM、UTF-8 (LISPSYS=1 または 2)。
(vl-load-com)
(setq kt:version "2026-10-30.1")

;; -------- 設定：換気設備への拡張時はこのプロファイルを追加する --------
(setq kt:config
  '((block . "KUCHO_KIKI") (sheet . "機器表 (空調設備)")
    (raw-sheet . "CAD_DATA") (header-row . 5) (start-row . 6)
    (detail-rows . 6) (pitch . 7) (first-floor-col . 10)
    (quantity-header . "数量") (note-header . "備考")
    (equipment-name . "空調調和機") (name-tag . nil)
    (remote-tag . "リモコン") (accessories . "その他付属品一式")
    ;; 帳票下部に注記等がある場合はデータ領域の最終行を明示する。
    ;; nil の場合、既存UsedRangeの最終行までを機器専用領域とする。
    (data-end-row . nil)))
(setq kt:tags '("SYSTEM" "NUM" "MAKER" "MODEL" "TYPE"
  "COOL_CAP" "HEAT_CAP" "COOL_POWER" "HEAT_POWER" "COMP_POWER" "FAN_IN"
  "FAN_OUT" "PHASE" "VOLT" "リモコン" "LOCATION" "GAS_PIPE" "LIQ_PIPE"
  "SYSTEM_TYPE" "FREQ" "FLOOR"))
(setq kt:required-tags '("SYSTEM" "NUM" "MODEL"))
;; 空調設定は既存どおり保持。カテゴリ設定はコマンド内のローカル束縛で切替。
(setq kt:aircon-config kt:config kt:aircon-tags kt:tags)
(setq kt:vent-tags '("SYSTEM" "NUM" "LOCATION" "FLOOR" "FLOOR_AREA" "CEILING_HEIGHT" "EQUIP_TYPE"
  "MAKER" "MODEL" "TYPE" "MOUNT_TYPE" "DUCT_DIA" "AIRFLOW"
  "STATIC_PRESSURE" "PHASE" "VOLT" "POWER" "NOISE"
  "TEMP_EX_EFF" "ENTHALPY_HEAT_EFF" "ENTHALPY_COOL_EFF" "ACCESSORY" "HANDLE"))
(setq kt:vent-config '((category . "KANKI") (block . "KANKI_KIKI")
  (sheet . "機器表 (換気設備)") (raw-sheet . "CAD_DATA_KANKI")
  (name-tag . "EQUIP_TYPE") (vent-first-row . 6) (vent-detail-row . 7)
  (vent-spacer-row . 12) (vent-min-rows . 2) (vent-gap . 1)))
(defun kt:category (/ answer)
  ;; 日本語キーワードの戻り値に依存せず、番号で明示的に判定する。
  (while (not (member answer '(1 2)))
    (initget 6)
    (setq answer (getint "\n設備カテゴリ：1=空調 / 2=換気 <1>："))
    (if (null answer) (setq answer 1))
    (if (not (member answer '(1 2))) (princ "\n1（空調）または2（換気）を入力してください。")))
  (princ (if (= answer 2) "\n選択カテゴリ：換気（KANKI_KIKI）" "\n選択カテゴリ：空調（KUCHO_KIKI）"))
  (if (= answer 2) "KANKI" "KUCHO"))

(defun kt:cfg (key) (cdr (assoc key kt:config)))
(defun kt:trim (s) (vl-string-trim " \t\r\n　" s))
(defun kt:get (data key) (if (assoc key data) (cdr (assoc key data)) ""))
(defun kt:raw-columns () (append '("SYSTEM" "NUM" "KIKI_NO") (cddr kt:tags)))
(defun kt:identity (data / system num)
  ;; 元属性の文字列は変更せず、識別時にだけ前後空白を除く。
  (setq system (kt:trim (kt:get data "SYSTEM")) num (kt:trim (kt:get data "NUM")))
  (if (and (/= system "") (/= num "")) (list system num)))
(defun kt:key (data / identity)
  (if (setq identity (kt:identity data)) (strcat (car identity) "-" (cadr identity)) ""))
(defun kt:derive (data)
  ;; 旧KIKI_NO属性が残っていても記号は必ずSYSTEM・NUMから計算する。
  (cons (cons "KIKI_NO" (kt:key data))
        (vl-remove-if '(lambda (entry) (= (car entry) "KIKI_NO")) data)))
(defun kt:validate-record (data handle / tag)
  (foreach tag kt:required-tags
    (if (= (kt:trim (kt:get data tag)) "")
      (kt:warn (strcat "Handle=" handle "：" tag "属性がないか、値が空欄です。")))))
(defun kt:warn (s) (if (not (member s kt:warnings)) (setq kt:warnings (cons s kt:warnings))))
(defun kt:fail (s) (setq kt:reason s) (exit))
(defun kt:trace-write (message / file)
  (if (and kt:log-path (setq file (open kt:log-path "a")))
    (progn
      (write-line (strcat (itoa (getvar "MILLISECS")) " " message) file)
      (close file))))
(defun kt:trace (message)
  ;; 画面がCOM待ちで更新されなくても直前の工程を残す。毎回closeして確定する。
  (vl-catch-all-apply 'kt:trace-write (list message))
  (princ (strcat "\nKIKITABLE：" message)) (princ))
(defun kt:timed (label function args / started result)
  (kt:trace (strcat label "開始"))
  (setq started (getvar "MILLISECS") result (apply function args))
  (kt:trace (strcat label "完了 / "
    (rtos (/ (- (getvar "MILLISECS") started) 1000.0) 2 3) "秒"))
  result)
(defun kt:join (items sep / out s)
  (setq out "")
  (foreach s items (if (/= s "") (setq out (if (= out "") s (strcat out sep s))))) out)
(defun kt:lines (items / out s)
  ;; 空行も保持：場所・階・備考の改行位置を揃える。
  (setq out (car items))
  (foreach s (cdr items) (setq out (strcat out "\n" s)))
  (if out out ""))

;; -------- COM管理：Variant型9も必ず展開し、所有した参照のみ解放 --------
(defun kt:unwrap (v)
  (while (= (type v) 'VARIANT) (setq v (vlax-variant-value v))) v)
(defun kt:own (v)
  (setq v (kt:unwrap v))
  (if (/= (type v) 'VLA-OBJECT) (kt:fail "COMオブジェクトを取得できませんでした。"))
  (setq kt:objects (cons v kt:objects)) v)
(defun kt:drop (o)
  (if (= (type o) 'VLA-OBJECT)
    (progn
      (vl-catch-all-apply 'vlax-release-object (list o))
      (setq kt:objects (vl-remove o kt:objects)))))
(defun kt:cleanup (/ o result)
  ;; 保存は成功経路で一度だけ行う。失敗・Escでは保存せず閉じる。
  (if kt:excel
    (vl-catch-all-apply 'vlax-put-property (list kt:excel 'DisplayAlerts :vlax-false)))
  ;; セル・シート・コレクションを、Excelが生きている間に先に解放する。
  (foreach o kt:objects
    (if (and (not (eq o kt:book)) (not (eq o kt:excel)))
      (vl-catch-all-apply 'vlax-release-object (list o))))
  (setq kt:objects nil)
  (if kt:book
    (progn
      (kt:trace "専用Excelブックを閉じる")
      (setq result (vl-catch-all-apply 'vlax-invoke-method (list kt:book 'Close :vlax-false)))
      (if (vl-catch-all-error-p result) (princ "\n警告：専用Excelブックを閉じられませんでした。"))
      (vl-catch-all-apply 'vlax-release-object (list kt:book))))
  (setq kt:objects nil kt:book nil)
  (if kt:excel
    (progn
      (kt:trace "専用Excelを終了")
      (setq result (vl-catch-all-apply 'vlax-invoke-method (list kt:excel 'Quit)))
      (if (vl-catch-all-error-p result) (princ "\n警告：専用Excelを終了できませんでした。"))
      (vl-catch-all-apply 'vlax-release-object (list kt:excel))))
  ;; COM参照は上で明示解放済み。Excel終了直後の強制GCは行わない。
  (setq kt:excel nil))
(defun kt:col (n / s)
  (setq s "")
  (while (> n 0)
    (setq n (1- n) s (strcat (chr (+ 65 (rem n 26))) s) n (fix (/ n 26)))) s)
(defun kt:address (r c) (strcat (kt:col c) (itoa r)))
(defun kt:range (ws r1 c1 r2 c2)
  (kt:own (vlax-get-property ws 'Range
    (kt:address r1 c1) (kt:address r2 c2))))
(defun kt:cell-value (ws row col / cell v)
  (setq cell (kt:range ws row col row col) v (vlax-get-property cell 'Value2))
  (if (and (= (type v) 'VARIANT) (= (vlax-variant-type v) 10))
    (kt:fail (strcat "Excelセルにエラーがあります：" (kt:address row col))))
  (setq v (kt:unwrap v)) (kt:drop cell) v)
(defun kt:clear (ws r1 c1 r2 c2 / area)
  (if (>= r2 r1)
    (progn
      (setq area (kt:range ws r1 c1 r2 c2))
      (vlax-invoke-method area 'ClearContents) (kt:drop area))))
(defun kt:last (ws axis / area parts n)
  (setq area (kt:own (vlax-get-property ws 'UsedRange))
        parts (kt:own (vlax-get-property area (if (= axis 'Row) 'Rows 'Columns)))
        n (+ (vlax-get-property area axis) (vlax-get-property parts 'Count) -1))
  (kt:drop parts) (kt:drop area) n)
(defun kt:put (ws row col value / cell merge)
  (if (and value (not (equal value "")))
    (progn
      (setq kt:cell-context (kt:address row col)
            cell (kt:range ws row col row col))
      ;; 結合セルの左上以外への書込みは値が消えるので中止する。
      (if (= (kt:unwrap (vlax-get-property cell 'MergeCells)) :vlax-true)
        (progn
          (setq merge (kt:own (vlax-get-property cell 'MergeArea)))
          (if (or (/= row (vlax-get-property merge 'Row))
                  (/= col (vlax-get-property merge 'Column)))
            (kt:fail (strcat kt:cell-context " は結合セルの左上ではありません。帳票の結合を確認してください。")))
          (kt:drop merge)))
      ;; 文字列は先頭アポストロフィで数式化・型番の自動変換を防ぐ。
      ;; NumberFormatは変えず、台数と最大電力は数値のまま書き込む。
      (vlax-put-property cell 'Value2 (if (= (type value) 'STR) (strcat "'" value) value))
      (kt:drop cell))))

(defun kt:excel-value (value)
  ;; 空欄は空欄、文字列はリテラル、台数・電力は数値を維持する。
  (if (= (type value) 'STR)
    (if (= value "") "" (strcat "'" value)) value))
(defun kt:put-matrix (ws row col matrix / area array height width)
  (if matrix
    (progn
      (setq height (length matrix) width (length (car matrix))
            array (vlax-make-safearray vlax-vbVariant (cons 1 height) (cons 1 width)))
      (vlax-safearray-fill array
        (mapcar '(lambda (values) (mapcar 'kt:excel-value values)) matrix))
      (setq kt:cell-context (kt:address row col)
            area (kt:range ws row col (+ row height -1) (+ col width -1)))
      (vlax-put-property area 'Value2 (vlax-make-variant array))
      (kt:drop area))))
(defun kt:write-plan (ws plan / item bottom right area merged array)
  ;; 結合なし帳票は一括転記。結合ありは従来の左上セル検査を維持する。
  (if plan
    (progn
      (setq bottom (kt:cfg 'start-row) right 2)
      (foreach item plan (setq bottom (max bottom (car item)) right (max right (cadr item))))
      (setq area (kt:range ws (kt:cfg 'start-row) 2 bottom right)
            merged (kt:unwrap (vlax-get-property area 'MergeCells)))
      (if (equal merged :vlax-false)
        (progn
          (setq array (vlax-make-safearray vlax-vbVariant
            (cons (kt:cfg 'start-row) bottom) (cons 2 right)))
          (foreach item plan
            (vlax-safearray-put-element array (car item) (cadr item) (kt:excel-value (caddr item))))
          (setq kt:cell-context (kt:address (kt:cfg 'start-row) 2))
          (vlax-put-property area 'Value2 (vlax-make-variant array)))
        (foreach item plan (kt:put ws (car item) (cadr item) (caddr item))))
      (kt:drop area))))

;; -------- 自然順ソートと数値判定（図面単位設定に依存させない） --------
(defun kt:digit (s) (and (= (strlen s) 1) (<= 48 (ascii s) 57)))
(defun kt:digits (s / i ok)
  (setq i 1 ok (/= s ""))
  (while (and ok (<= i (strlen s)))
    (setq ok (kt:digit (substr s i 1)) i (1+ i))) ok)
(defun kt:unzero (s)
  (while (and (> (strlen s) 1) (= (substr s 1 1) "0")) (setq s (substr s 2))) s)
(defun kt:floor (s) (if (kt:digits (kt:trim s)) (kt:unzero (kt:trim s))))
(defun kt:number (s / i dots digits ok ch)
  ;; 非負の十進数だけを受け付ける。単位・乗算式・部分数値は採用しない。
  (setq s (kt:trim s) i 1 dots 0 digits 0 ok (/= s ""))
  (while (and ok (<= i (strlen s)))
    (setq ch (substr s i 1))
    (cond ((kt:digit ch) (setq digits (1+ digits)))
          ((= ch ".") (setq dots (1+ dots) ok (<= dots 1)))
          (T (setq ok nil)))
    (setq i (1+ i)))
  (if (and ok (> digits 0)) (atof s)))
(defun kt:str-less (a b / i lim)
  (setq i 1 lim (min (strlen a) (strlen b)))
  (while (and (<= i lim) (= (substr a i 1) (substr b i 1))) (setq i (1+ i)))
  (if (> i lim) (< (strlen a) (strlen b)) (< (ascii (substr a i 1)) (ascii (substr b i 1)))))
(defun kt:tokens (s / i chunk numeric next out ch)
  (setq i 1 chunk "")
  (while (<= i (strlen s))
    (setq ch (substr s i 1) next (kt:digit ch))
    (if (and (/= chunk "") (not (equal numeric next)))
      (setq out (cons (cons numeric chunk) out) chunk ""))
    (setq numeric next chunk (strcat chunk ch) i (1+ i)))
  (if (/= chunk "") (setq out (cons (cons numeric chunk) out))) (reverse out))
(defun kt:natural-less (a b / aa bb x y decided result)
  (setq aa (kt:tokens (strcase a)) bb (kt:tokens (strcase b)))
  (while (and aa bb (not decided))
    (setq x (cdar aa) y (cdar bb))
    (if (and (caar aa) (caar bb)) (setq x (kt:unzero x) y (kt:unzero y)))
    (if (/= x y)
      (setq decided T result
        (if (and (caar aa) (caar bb) (/= (strlen x) (strlen y)))
          (< (strlen x) (strlen y)) (kt:str-less x y))))
    (setq aa (cdr aa) bb (cdr bb)))
  (if decided result
    (cond (aa nil) (bb T) (T (kt:str-less a b)))))

;; -------- CAD読取り：全空間の直接配置ブロック（動的ブロック対応） --------
(defun kt:array (v)
  (setq v (kt:unwrap v))
  ;; GetConstantAttributesは定数属性がないと空のSAFEARRAYを返す。
  ;; 空配列へのsafearray->listは「インデックスが無効です」になる。
  ;; 本当のCOMエラーは握り潰さず、空と確認できた場合だけnilにする。
  (if (= (type v) 'SAFEARRAY)
    (if (or (= (vlax-safearray-get-dim v) 0)
            (< (vlax-safearray-get-u-bound v 1) (vlax-safearray-get-l-bound v 1)))
      nil (vlax-safearray->list v))
    v))
(defun kt:attribute-objects (obj method / result a objects)
  (setq kt:stage (strcat "図面属性の収集 / Handle=" (vla-get-Handle obj)
                         " / " (vl-symbol-name method)))
  (setq result (kt:array (vlax-invoke-method obj method)))
  ;; 次の取得処理が失敗しても、既に取得した参照を解放できるようにする。
  (foreach a result (setq objects (cons (kt:own a) objects)))
  (reverse objects))
(defun kt:read-attrs (obj / attributes a tag data)
  (if (= (vla-get-HasAttributes obj) :vlax-true)
    (setq attributes (append (kt:attribute-objects obj 'GetAttributes)
                            (kt:attribute-objects obj 'GetConstantAttributes))))
  (setq kt:stage (strcat "図面属性の収集 / Handle=" (vla-get-Handle obj) " / 属性値の読取り"))
  (foreach a attributes
    (setq tag (strcase (kt:trim (vla-get-TagString a))))
    (if (assoc tag data)
      (kt:fail (strcat "属性タグが重複しています。Handle=" (vla-get-Handle obj) " / " tag)))
    (setq data (cons (cons tag (vla-get-TextString a)) data))
    (if (not (member tag kt:raw-tags)) (setq kt:raw-tags (append kt:raw-tags (list tag))))
    (kt:drop a))
  (kt:validate-record data (vla-get-Handle obj))
  (cons (cons "HANDLE" (vla-get-Handle obj)) (kt:derive data)))
(defun kt:collect (/ ss i obj name data records)
  (setq ss (ssget "_X" '((0 . "INSERT"))) i 0)
  (if ss
    (repeat (sslength ss)
      (setq obj (kt:own (vlax-ename->vla-object (ssname ss i))) i (1+ i))
      (setq name (if (vlax-property-available-p obj 'EffectiveName)
                   (vla-get-EffectiveName obj) (vla-get-Name obj)))
      (if (= (strcase name) (strcase (kt:cfg 'block)))
        (progn
          ;; MINSERTは1実体が複数台を表すため黙って1台として数えない。
          (if (= (vla-get-ObjectName obj) "AcDbMInsertBlock")
            (kt:fail "配列複写ブロック(MINSERT)には対応していません。通常ブロックに展開してください。"))
          (setq data (kt:read-attrs obj))
          (if (= (kt:key data) "")
            (kt:warn (strcat "Handle=" (vla-get-Handle obj) "：SYSTEM・NUMから機器記号を生成できません。CAD_DATAだけに出力します。")))
          (setq records (cons data records))))
      (kt:drop obj)))
  (reverse records))

;; -------- 集計・仕様文章：同一記号の矛盾項目は採用せず空欄にする --------
(defun kt:group-less (a b / ai bi)
  (setq ai (kt:identity (cadr a)) bi (kt:identity (cadr b)))
  (if (= (car ai) (car bi))
    (kt:natural-less (cadr ai) (cadr bi))
    (kt:natural-less (car ai) (car bi))))
(defun kt:group (records / record identity found groups)
  (foreach record records
    (if (setq identity (kt:identity record))
      (if (setq found (assoc identity groups))
        (setq groups (subst (cons identity (append (cdr found) (list record))) found groups))
        (setq groups (cons (list identity record) groups)))))
  ;; SYSTEMとNUMの組で集約し、表示用の記号は最後に作る。
  (setq groups (mapcar '(lambda (g) (cons (kt:key (cadr g)) (cdr g))) groups))
  (vl-sort groups 'kt:group-less))
(defun kt:unique-values (records tag / values record value)
  (foreach record records
    (setq value (kt:trim (kt:get record tag)))
    (if (not (member value values)) (setq values (append values (list value))))) values)
(defun kt:consensus (key records / tag values data labels v)
  (foreach tag (if (kt:cfg 'name-tag) (cons (kt:cfg 'name-tag) kt:tags) kt:tags)
    (if (not (member tag '("SYSTEM" "NUM" "LOCATION" "FLOOR" "FLOOR_AREA" "CEILING_HEIGHT" "NOTE" "HANDLE")))
      (progn
        (setq values (kt:unique-values records tag))
        (if (> (length values) 1)
          (progn
            (setq labels nil)
            (foreach v values (setq labels (cons (if (= v "") "(空欄)" v) labels)))
            (kt:warn (strcat key " の " tag " が一致していません："
                      (kt:join (reverse labels) " / ") "。該当項目は空欄。"))
            (setq data (cons (cons tag "") data)))
          (setq data (cons (cons tag (car values)) data)))))) data)
(defun kt:power-text (s / p)
  (if (= s "") ""
    (if (setq p (vl-string-search "×" s))
      (strcat (substr s 1 p) "kW" (substr s (1+ p))) (strcat s "kW"))))
(defun kt:phrase (label value) (if (= value "") "" (strcat label (kt:power-text value))))
(defun kt:capacity (value / number text)
  ;; 能力だけを小数第1位に揃える。DIMZINで末尾0が省略されても補う。
  (if (setq number (kt:number value))
    (progn
      (setq text (rtos number 2 1))
      (if (= (substr text 1 1) ".") (setq text (strcat "0" text)))
      (if (not (vl-string-search "." text)) (setq text (strcat text ".0"))))
    (setq text value))
  text)
(defun kt:phase-text (value)
  ;; 帳票の電源欄だけ相記号を除く。元属性・CAD_DATAは変更しない。
  (kt:trim (vl-string-translate "φΦϕ" "   " value)))
(defun kt:spec (data)
  (list (kt:get data "SYSTEM_TYPE") (kt:get data "TYPE")
    (kt:join (list (kt:phrase "冷房能力" (kt:capacity (kt:get data "COOL_CAP")))
                   (kt:phrase "暖房能力" (kt:capacity (kt:get data "HEAT_CAP")))) "　")
    (kt:join (list (kt:phrase "定格冷房標準消費電力" (kt:get data "COOL_POWER"))
                   (kt:phrase "定格暖房標準消費電力" (kt:get data "HEAT_POWER"))) "／")
    (kt:join (list (kt:phrase "圧縮機出力" (kt:get data "COMP_POWER"))
                   (kt:phrase "室内送風機出力" (kt:get data "FAN_IN"))
                   (kt:phrase "室外送風機出力" (kt:get data "FAN_OUT"))) "　")
    ;; リモコン未入力時は余計な読点や機種名を補わない。
    (kt:join (list (kt:get data (kt:cfg 'remote-tag)) (kt:cfg 'accessories)) "、")))
(defun kt:max-power (key data / a b av bv)
  (setq a (kt:get data "COOL_POWER") b (kt:get data "HEAT_POWER")
        av (kt:number a) bv (kt:number b))
  (cond
    ((and av bv) (max av bv))
    ((and (= a "") (= b "")) nil)
    (T (kt:warn (strcat key "：冷房・暖房消費電力の両方を数値として取得できません。kW欄は空欄。")) nil)))
(defun kt:locations (key records floors / record location floor raw note identity found buckets)
  ;; 備考の異なる個体は別行。場所・階・備考が一致する場合だけ台数をまとめる。
  (foreach record records
    (setq location (kt:trim (kt:get record "LOCATION")) raw (kt:trim (kt:get record "FLOOR"))
          floor (kt:floor raw) note (kt:trim (kt:get record "NOTE")))
    (if (= location "") (kt:warn (strcat key "：LOCATIONが空欄です。")))
    (cond ((null floor) (kt:warn (strcat key "：FLOORが空欄または整数以外です：" raw)))
          ((not (assoc floor floors)) (kt:warn (strcat key "：" floor "F列がExcelにありません。総数量には含めます。"))))
    (setq identity (list location (if floor floor raw) note))
    (if (setq found (assoc identity buckets))
      (setq buckets (subst (cons identity (1+ (cdr found))) found buckets))
      (setq buckets (append buckets (list (cons identity 1)))))) buckets)
(defun kt:location-text (bucket / name count)
  (setq name (caar bucket) count (cdr bucket))
  (if (and (/= name "") (> count 1)) (strcat name "(" (itoa count) ")") name))
(defun kt:add-plan (row col value)
  (if (and value (not (equal value ""))) (setq kt:plan (cons (list row col value) kt:plan))))
(defun kt:plan-group (group index floors quantity note-col / key records data start specs i buckets bucket notes common slot tail floor texts values notes-out count)
  (setq key (car group) records (cdr group) data (kt:consensus key records)
        start (+ (kt:cfg 'start-row) (* index (kt:cfg 'pitch)))
        specs (kt:spec data) buckets (kt:locations key records floors)
        notes (kt:unique-values records "NOTE") common (= (length notes) 1))
  (kt:add-plan start 2 key)
  (kt:add-plan start 3 (if (kt:cfg 'name-tag) (kt:get data (kt:cfg 'name-tag)) (kt:cfg 'equipment-name)))
  (kt:add-plan start 4 (kt:get data "MAKER"))
  (kt:add-plan (1+ start) 4 (kt:get data "MODEL"))
  (setq i 0)
  (foreach slot specs (kt:add-plan (+ start i) 5 slot) (setq i (1+ i)))
  (kt:add-plan start 7 (kt:phase-text (kt:get data "PHASE")))
  (kt:add-plan start 8 (kt:get data "VOLT"))
  (kt:add-plan start 9 (kt:max-power key data))
  (if common (kt:add-plan start note-col (car notes)))
  (if (> (length buckets) (kt:cfg 'detail-rows))
    (kt:warn (strcat key " の設置場所行が6行を超えています。6行目に改行で全件格納しました。機器表の行高とCAD_DATAを確認してください。")))
  (setq i 0 tail buckets)
  (while tail
    (setq slot (+ start i))
    (if (and (= i (1- (kt:cfg 'detail-rows))) (cdr tail))
      (progn
        (setq texts nil notes-out nil)
        (foreach bucket tail
          (setq texts (cons (kt:location-text bucket) texts)
                notes-out (cons (caddr (car bucket)) notes-out)))
        (kt:add-plan slot 6 (kt:lines (reverse texts)))
        (if (not common) (kt:add-plan slot note-col (kt:lines (reverse notes-out))))
        (foreach floor floors
          (setq values nil)
          (foreach bucket tail
            (setq values (cons (if (= (cadr (car bucket)) (car floor)) (itoa (cdr bucket)) "") values)))
          (kt:add-plan slot (cdr floor) (kt:lines (reverse values))))
        (setq tail nil))
      (progn
        (setq bucket (car tail))
        (kt:add-plan slot 6 (kt:location-text bucket))
        (if (setq floor (assoc (cadr (car bucket)) floors)) (kt:add-plan slot (cdr floor) (cdr bucket)))
        (if (not common) (kt:add-plan slot note-col (caddr (car bucket))))
        (setq tail (cdr tail))))
    (setq i (1+ i)))
  (kt:add-plan (+ start (1- (min (length buckets) (kt:cfg 'detail-rows)))) quantity (length records)))

;; -------- Excelを安全に開く：既存ユーザーExcelを所有・終了しない --------
(defun kt:already-open (path / folder lock)
  ;; 応答しない既存ExcelへのWorkbooks照会は行わない。
  ;; 所有者ファイルは事前チェック。存在しない場合もOpen後のReadOnlyで検証。
  ;; 残存ロックは安全側で中止し、自動削除しない。
  (kt:trace "01 対象ファイルのロック確認（既存Excelへ接続しません）")
  (setq folder (vl-filename-directory path)
        lock (strcat (if folder (strcat folder "\\") "") "~$"
                     (vl-filename-base path) (vl-filename-extension path)))
  (findfile lock))
(defun kt:open (path / books)
  (setq path (vl-string-translate "/" "\\" path) kt:stage "対象ファイルのロック確認")
  (if (kt:already-open path)
    (kt:fail "対象Excelのロックファイルがあります。対象ブックを閉じて再実行してください。閉じても出る場合は残存ロックを確認してください。"))
  (setq kt:stage "専用Excel生成") (kt:trace "05 専用Excel生成")
  (setq kt:excel (vlax-create-object "Excel.Application"))
  (setq kt:stage "専用Excel設定") (kt:trace "06 専用Excel設定")
  (vlax-put-property kt:excel 'Visible :vlax-false)
  (vlax-put-property kt:excel 'DisplayAlerts :vlax-false)
  (vlax-put-property kt:excel 'EnableEvents :vlax-false)
  (vlax-put-property kt:excel 'ScreenUpdating :vlax-false)
  (vlax-put-property kt:excel 'AutomationSecurity 3)
  (setq books (kt:own (vlax-get-property kt:excel 'Workbooks)))
  ;; UpdateLinks=0 / ReadOnly=False / Password="" / Notify=False。
  ;; 別Excelインスタンスがロックしている場合もReadOnlyを確認して中止する。
  (setq kt:stage "対象ブックを開く") (kt:trace "07 Workbook.Open開始")
  (setq kt:book (kt:own (vlax-invoke-method books 'Open path 0 :vlax-false
                         5 "" "" :vlax-true 2 "" :vlax-false :vlax-false)))
  (setq kt:stage "書込み権限確認") (kt:trace "08 Workbook.Open完了・書込み権限確認")
  (if (= (kt:unwrap (vlax-get-property kt:book 'ReadOnly)) :vlax-true)
    (kt:fail "対象Excelが開かれているか、読み取り専用です。Excelを閉じ、書込み権限を確認して再実行してください。"))
  ;; OneDrive等の自動保存で途中状態が保存されることを防ぐ。
  (if (vlax-property-available-p kt:book 'AutoSaveOn)
    (if (= (kt:unwrap (vlax-get-property kt:book 'AutoSaveOn)) :vlax-true)
      (vlax-put-property kt:book 'AutoSaveOn :vlax-false))))
(defun kt:sheet (sheets name / result)
  (setq result (vl-catch-all-apply 'vlax-get-property (list sheets 'Item name)))
  (if (not (vl-catch-all-error-p result)) (kt:own result)))
(defun kt:headers (ws / col last value floor floors quantity note-col)
  (setq col (kt:cfg 'first-floor-col) last (kt:last ws 'Column))
  (while (<= col last)
    (setq value (kt:cell-value ws (kt:cfg 'header-row) col))
    (if (= (type value) 'STR)
      (progn
        (setq value (strcase (kt:trim value)) floor nil)
        (if (and (> (strlen value) 1) (= (substr value (strlen value)) "F"))
          (setq floor (kt:floor (substr value 1 (1- (strlen value))))))
        (cond
          (floor
            (if (assoc floor floors) (kt:fail (strcat value "見出しが重複しています。")))
            (setq floors (cons (cons floor col) floors)))
          ((= value (kt:cfg 'quantity-header))
            (if quantity (kt:fail "数量見出しが重複しています。")) (setq quantity col))
          ((= value (kt:cfg 'note-header))
            (if note-col (kt:fail "備考見出しが重複しています。")) (setq note-col col)))))
    (setq col (1+ col)))
  (if (or (null floors) (null quantity) (null note-col))
    (kt:fail "5行目のJ列以降に、階(1F等)・数量・備考の見出しが必要です。"))
  (if (or (<= note-col quantity) (vl-some '(lambda (f) (>= (cdr f) quantity)) floors))
    (kt:fail "階列 → 数量 → 備考の順に見出しを配置してください。"))
  (list (reverse floors) quantity note-col))

;; -------- 書式展開・出力：既存セルの書式を維持して内容だけを更新 --------
(defun kt:check-boundary (ws end col / r c cell merge rows columns bottom right area merged)
  ;; ヘッダーや領域外に及ぶ結合セルをClearContentsで壊さない。
  (setq r (kt:cfg 'start-row))
  ;; 範囲全体が結合なしなら、セルごとのCOM照会は不要。
  ;; 混在時のNullも結合ありとして扱い、従来の厳密な境界検査へ進む。
  (setq area (kt:range ws r 2 end col)
        merged (kt:unwrap (vlax-get-property area 'MergeCells)))
  (kt:drop area)
  (if (equal merged :vlax-false) (setq r (1+ end)))
  (while (<= r end)
    (setq c 2)
    (while (<= c col)
      (setq cell (kt:range ws r c r c))
      (if (= (kt:unwrap (vlax-get-property cell 'MergeCells)) :vlax-true)
        (progn
          (setq merge (kt:own (vlax-get-property cell 'MergeArea))
                rows (kt:own (vlax-get-property merge 'Rows))
                columns (kt:own (vlax-get-property merge 'Columns))
                bottom (+ (vlax-get-property merge 'Row) (vlax-get-property rows 'Count) -1)
                right (+ (vlax-get-property merge 'Column) (vlax-get-property columns 'Count) -1))
          (if (or (< (vlax-get-property merge 'Row) (kt:cfg 'start-row))
                  (< (vlax-get-property merge 'Column) 2) (> bottom end) (> right col)
                  (/= (fix (/ (- r (kt:cfg 'start-row)) (kt:cfg 'pitch)))
                      (fix (/ (- bottom (kt:cfg 'start-row)) (kt:cfg 'pitch)))))
            (kt:fail (strcat (kt:address r c) "：結合セルが機器枠または出力領域をまたいでいます。")))
          (kt:drop columns) (kt:drop rows) (kt:drop merge)))
      (kt:drop cell) (setq c (1+ c)))
    (setq r (1+ r))))
(defun kt:extend (ws oldend newend lastcol / source dest index row i source-row dest-row heights)
  (setq row (kt:cfg 'start-row) i 0)
  (repeat (kt:cfg 'pitch)
    (setq source-row (kt:range ws (+ row i) 2 (+ row i) 2)
          heights (append heights (list (vlax-get-property source-row 'RowHeight))))
    (kt:drop source-row) (setq i (1+ i)))
  (setq source (kt:range ws row 2 (+ row (1- (kt:cfg 'pitch))) lastcol)
        index 1)
  (while (<= (+ row (* index (kt:cfg 'pitch))) newend)
    (setq i (+ row (* index (kt:cfg 'pitch))))
    (if (> (+ i (1- (kt:cfg 'pitch))) oldend)
      (progn
        (setq dest (kt:range ws i 2 (+ i (1- (kt:cfg 'pitch))) lastcol))
        ;; Destination指定Copyはクリップボードを使わず結合・書式も引き継ぐ。
        ;; コピーした内容は後続ClearContentsで消す。
        (vlax-invoke-method source 'Copy dest) (kt:drop dest)
        ;; 高さはRange.Copyで継承されないため明示する。
        (setq dest-row 0)
        (foreach source-row heights
          (setq dest (kt:range ws (+ i dest-row) 2 (+ i dest-row) 2))
          (vlax-put-property dest 'RowHeight source-row)
          (kt:drop dest) (setq dest-row (1+ dest-row)))))
    (setq index (1+ index)))
  (kt:drop source))
(defun kt:print-area (ws end lastcol / setup text area areas rows columns top left right bottom)
  (setq setup (kt:own (vlax-get-property ws 'PageSetup))
        text (vlax-get-property setup 'PrintArea))
  (if (/= text "")
    (progn
      (setq area (kt:own (vlax-get-property ws 'Range text text))
            areas (kt:own (vlax-get-property area 'Areas)))
      (if (/= (vlax-get-property areas 'Count) 1)
        (kt:fail "印刷範囲が複数に分かれています。機器表の連続した範囲に設定してください。"))
      (setq rows (kt:own (vlax-get-property area 'Rows))
            columns (kt:own (vlax-get-property area 'Columns))
            top (vlax-get-property area 'Row) left (vlax-get-property area 'Column)
            bottom (+ top (vlax-get-property rows 'Count) -1)
            right (+ left (vlax-get-property columns 'Count) -1))
      (if (or (> top (kt:cfg 'header-row)) (> left 2))
        (kt:fail "既存印刷範囲に機器表の見出しとB列が含まれていません。"))
      (if (or (> end bottom) (> lastcol right))
        (vlax-put-property setup 'PrintArea
          (strcat (kt:address top left) ":" (kt:address (max end bottom) (max lastcol right)))))
      (kt:drop columns) (kt:drop rows) (kt:drop areas) (kt:drop area)))
  (kt:drop setup))
(defun kt:write-raw (ws records / row col tag record end width area merged chunk)
  (setq end (max (kt:last ws 'Row) (1+ (length records)))
        width (max (kt:last ws 'Column) (length kt:raw-tags)))
  (kt:clear ws 1 1 end width)
  (setq area (kt:range ws 1 1 (1+ (length records)) (length kt:raw-tags))
        merged (kt:unwrap (vlax-get-property area 'MergeCells)))
  (kt:drop area)
  (if (equal merged :vlax-false)
    (progn
      ;; 500行ずつ書くため、台数が増えてもCOM往復数はセル数に比例しない。
      (setq row 1 chunk (list kt:raw-tags))
      (foreach record records
        (setq record (kt:derive record)
              chunk (cons (mapcar '(lambda (tag) (kt:get record tag)) kt:raw-tags) chunk))
        (if (>= (length chunk) 500)
          (progn
            (kt:put-matrix ws row 1 (reverse chunk))
            (setq row (+ row (length chunk)) chunk nil))))
      (kt:put-matrix ws row 1 (reverse chunk)))
    (progn
      (setq col 1)
      (foreach tag kt:raw-tags (kt:put ws 1 col tag) (setq col (1+ col)))
      (setq row 2)
      (foreach record records
        (setq record (kt:derive record))
        (setq col 1)
        (foreach tag kt:raw-tags
          (kt:put ws row col (kt:get record tag)) (setq col (1+ col)))
        (setq row (1+ row))))))
(defun kt:write-aircon-book (records groups / sheets ws raw headers floors quantity note-col index group oldend newend end item limit)
  (setq sheets (kt:own (vlax-get-property kt:book 'Worksheets))
        ws (kt:sheet sheets (kt:cfg 'sheet)))
  (if (null ws) (kt:fail (strcat "シートが存在しません：" (kt:cfg 'sheet))))
  (setq headers (kt:headers ws) floors (car headers) quantity (cadr headers) note-col (caddr headers)
        index 0 kt:plan nil)
  (foreach group groups (kt:plan-group group index floors quantity note-col) (setq index (1+ index)))
  (setq oldend (max (+ (kt:cfg 'start-row) (1- (kt:cfg 'pitch))) (kt:last ws 'Row))
        newend (+ (kt:cfg 'start-row) (* (max 1 (length groups)) (kt:cfg 'pitch)) -1)
        limit (kt:cfg 'data-end-row))
  (if limit
    (progn
      (if (> newend limit) (kt:fail "機器数が設定data-end-rowの出力領域を超えます。"))
      (setq oldend limit)))
  (setq end (max oldend newend))
  (kt:timed "結合セル境界検査" 'kt:check-boundary (list ws end note-col))
  (setq kt:stage "帳票書式の展開")
  (kt:timed "帳票書式展開" 'kt:extend (list ws oldend newend note-col))
  (kt:clear ws (kt:cfg 'start-row) 2 end note-col)
  (setq kt:stage "完成機器表の書込み")
  (kt:timed "完成機器表書込み" 'kt:write-plan (list ws (reverse kt:plan)))
  (kt:print-area ws newend note-col)
  (setq kt:stage "CAD_DATAの書込み" raw (kt:sheet sheets (kt:cfg 'raw-sheet)))
  (if (null raw)
    (progn
      (setq raw (kt:own (vlax-invoke-method sheets 'Add)))
      (vlax-put-property raw 'Name (kt:cfg 'raw-sheet))))
  (kt:timed "CAD_DATA書込み" 'kt:write-raw (list raw records)))
;; -------- 換気：可変行の配置計画と専用の書式展開 --------
(defun kt:vent-part (data tag suffix / value)
  (setq value (kt:get data tag))
  (if (= value "") "" (strcat value suffix)))
(defun kt:vent-accessory (data / value)
  (setq value (kt:trim (kt:get data "ACCESSORY")))
  (if (= value "") (kt:cfg 'accessories) value))
;; 将来のエンタルピー効率行は、この関数の返すリストへ追加できる。
;; 現時点では温度交換効率だけを能力行へ表示する。
(defun kt:heat-exchanger-spec (data capacity / efficiency)
  (setq efficiency (kt:trim (kt:get data "TEMP_EX_EFF")))
  (list (kt:get data "TYPE")
    (kt:join (list capacity (if (= efficiency "") ""
      (strcat "温度交換効率 " efficiency "%"))) " ")
    (kt:vent-accessory data)))
(defun kt:vent-spec (data / capacity)
  (setq capacity (kt:join (list (kt:vent-part data "DUCT_DIA" "φ")
    (kt:vent-part data "AIRFLOW" "m3/h") (kt:vent-part data "STATIC_PRESSURE" "Pa")) " × "))
  (setq capacity (if (= capacity "") "" (strcat "能力 " capacity)))
  (if (= (kt:trim (kt:get data "EQUIP_TYPE")) "全熱交換器")
    (kt:heat-exchanger-spec data capacity)
    ;; 通常換気扇は従来の2行構成をそのまま維持する。
    (list (kt:get data "TYPE") capacity)))
(defun kt:vent-power (key data / value number)
  (setq value (kt:get data "POWER") number (kt:number value))
  (if (and (/= value "") (null number))
    (kt:warn (strcat key "：POWERが数値ではありません。kW欄は空欄。"))) number)
(defun kt:plan-vent (groups floors quantity note-col / start layouts group key records data buckets specs height i bucket floor text)
  (setq start (kt:cfg 'start-row) kt:plan nil)
  (foreach group groups
    (setq key (car group) records (cdr group) data (kt:consensus key records)
          buckets (kt:locations key records floors) specs (kt:vent-spec data)
          height (max (kt:cfg 'vent-min-rows) (length specs) (length buckets)))
    (kt:add-plan start 2 key)
    (kt:add-plan start 3 (kt:get data "EQUIP_TYPE"))
    (kt:add-plan start 4 (kt:get data "MAKER"))
    (kt:add-plan (1+ start) 4 (kt:get data "MODEL"))
    (setq i 0)
    (foreach text specs (kt:add-plan (+ start i) 5 text) (setq i (1+ i)))
    (kt:add-plan start 7 (kt:phase-text (kt:get data "PHASE")))
    (kt:add-plan start 8 (kt:get data "VOLT"))
    (kt:add-plan start 9 (kt:vent-power key data))
    (setq i 0)
    (foreach bucket buckets
      (kt:add-plan (+ start i) 6 (kt:location-text bucket))
      (if (setq floor (assoc (cadr (car bucket)) floors))
        (kt:add-plan (+ start i) (cdr floor) (cdr bucket)))
      (setq i (1+ i)))
    (kt:add-plan (+ start (max 0 (1- (length buckets)))) quantity (length records))
    (setq layouts (cons (list start height) layouts)
          start (+ start height (kt:cfg 'vent-gap))))
  (list (reverse layouts) (1- start)))
(defun kt:vent-end (ws / setup text area areas rows columns end)
  ;; UsedRange下端にはグリル表等があるため使わない。印刷範囲を更新領域にする。
  (setq setup (kt:own (vlax-get-property ws 'PageSetup)) text (vlax-get-property setup 'PrintArea))
  (if (= text "") (kt:fail "換気表の印刷範囲が未設定です。機器データ領域を設定してください。"))
  (setq area (kt:own (vlax-get-property ws 'Range text text))
        areas (kt:own (vlax-get-property area 'Areas))
        rows (kt:own (vlax-get-property area 'Rows)))
  (if (or (/= (vlax-get-property areas 'Count) 1)
          (/= (vlax-get-property area 'Row) (kt:cfg 'header-row))
          (/= (vlax-get-property area 'Column) 2))
    (kt:fail "換気表の印刷範囲はB5から始まる連続した機器表領域にしてください。"))
  (setq end (+ (vlax-get-property area 'Row) (vlax-get-property rows 'Count) -1))
  (if (< end (+ (kt:cfg 'start-row) (kt:cfg 'vent-min-rows)))
    (kt:fail "換気表の書式テンプレート行・区切り空行が印刷範囲外です。"))
  (kt:drop rows) (kt:drop areas) (kt:drop area) (kt:drop setup) end)
(defun kt:vent-check-merge (ws end lastcol / area merged)
  ;; 現行の実帳票はデータ部に結合なし。未知の結合を解除して壊さず中止する。
  (setq area (kt:range ws (kt:cfg 'start-row) 2 end lastcol)
        merged (kt:unwrap (vlax-get-property area 'MergeCells)))
  (kt:drop area)
  (if (not (equal merged :vlax-false))
    (kt:fail "換気表のデータ領域に結合セルがあります。可変行に対応する結合なしのテンプレートを使用してください。")))
(defun kt:vent-copy-row (source-sheet source-row dest-sheet dest-row lastcol / source dest height)
  (setq source (kt:range source-sheet source-row 2 source-row lastcol)
        dest (kt:range dest-sheet dest-row 2 dest-row lastcol)
        height (vlax-get-property source 'RowHeight))
  (vlax-invoke-method source 'Copy dest)
  (vlax-put-property dest 'RowHeight height)
  (kt:drop dest) (kt:drop source))
(defun kt:vent-spacer (ws end lastcol / row area values blank found value)
  ;; 再実行後は空行位置も変わる。最初の空の区切り行を実データから探す。
  (setq row (+ (kt:cfg 'start-row) (kt:cfg 'vent-min-rows)))
  (while (and (<= row end) (not found))
    (setq area (kt:range ws row 2 row lastcol)
          values (car (vlax-safearray->list (kt:unwrap (vlax-get-property area 'Value2)))) blank T)
    (kt:drop area)
    (foreach value values
      (setq value (kt:unwrap value))
      (if (and value (not (equal value ""))) (setq blank nil)))
    (if blank (setq found row)) (setq row (1+ row)))
  (if (not found) (kt:fail "換気表の区切り空行がありません。テンプレートを確認してください。")) found)
(defun kt:write-vent-book (records groups / sheets ws raw headers floors quantity note-col oldend newend layout layouts temp area item row height i spacer started)
  (setq sheets (kt:own (vlax-get-property kt:book 'Worksheets)) ws (kt:sheet sheets (kt:cfg 'sheet)))
  (if (null ws) (kt:fail (strcat "シートが存在しません：" (kt:cfg 'sheet))))
  (setq headers (kt:headers ws) floors (car headers) quantity (cadr headers) note-col (caddr headers)
        oldend (kt:vent-end ws) layout (kt:plan-vent groups floors quantity note-col)
        layouts (car layout) newend (max oldend (cadr layout)))
  (kt:vent-check-merge ws oldend note-col)
  (setq spacer (kt:vent-spacer ws oldend note-col))
  (setq kt:stage "換気表の可変行・書式展開")
  (kt:trace "換気表書式展開開始") (setq started (getvar "MILLISECS"))
  ;; 先頭・明細・空行の書式を一時シートへ退避。正常時は保存前に削除する。
  ;; エラー時はブックを保存しない既存ハンドラに任せる。
  (setq temp (kt:own (vlax-invoke-method sheets 'Add)))
  (kt:vent-copy-row ws (kt:cfg 'vent-first-row) temp 1 note-col)
  (kt:vent-copy-row ws (kt:cfg 'vent-detail-row) temp 2 note-col)
  (kt:vent-copy-row ws spacer temp 3 note-col)
  (if (> newend oldend)
    (progn
      ;; 下部の別表・注記は上書きせず行ごと下へ移動する。
      (setq area (kt:own (vlax-get-property ws 'Range
        (strcat (itoa (1+ oldend)) ":" (itoa newend))
        (strcat (itoa (1+ oldend)) ":" (itoa newend)))))
      (setq kc:row-shifts (cons (list (vlax-get-property ws 'Name) oldend (- newend oldend)) kc:row-shifts))
      (vlax-invoke-method area 'Insert -4121) (kt:drop area)))
  (foreach layout layouts
    (setq row (car layout) height (cadr layout) i 0)
    (repeat height
      (kt:vent-copy-row temp (if (= i 0) 1 2) ws (+ row i) note-col)
      (setq i (1+ i)))
    (repeat (kt:cfg 'vent-gap)
      (kt:vent-copy-row temp 3 ws (+ row i) note-col) (setq i (1+ i))))
  (kt:trace (strcat "換気表書式展開完了 / "
    (rtos (/ (- (getvar "MILLISECS") started) 1000.0) 2 3) "秒"))
  (kt:clear ws (kt:cfg 'start-row) 2 newend note-col)
  (setq kt:stage "換気表の書込み")
  (kt:timed "換気機器表書込み" 'kt:write-plan (list ws (reverse kt:plan)))
  (kt:print-area ws newend note-col)
  (vlax-invoke-method temp 'Delete) (kt:drop temp)
  (setq raw (kt:sheet sheets (kt:cfg 'raw-sheet)))
  (if (null raw)
    (progn (setq raw (kt:own (vlax-invoke-method sheets 'Add)))
           (vlax-put-property raw 'Name (kt:cfg 'raw-sheet))))
  (setq kt:stage "CAD_DATA_KANKIの書込み")
  (kt:timed "CAD_DATA_KANKI書込み" 'kt:write-raw (list raw records)))
(defun kt:write-book (records groups / calculation result)
  ;; セル書込み・行コピーのたびに他シートの数式を再計算しない。
  ;; 専用Excelだけを変更し、成功時は保存前に元の計算モードへ戻す。
  (setq calculation (kt:unwrap (vlax-get-property kt:excel 'Calculation)))
  (vlax-put-property kt:excel 'Calculation -4135)
  (if (= (kt:cfg 'category) "KANKI")
    (progn
      (vlax-invoke-method kt:excel 'CalculateFull)
      (setq kc:row-shifts nil kc:baseline (kc:errors))
      (kt:timed "換気計算表" 'kc:write (list records))
      (setq result (kt:write-vent-book records groups)))
    (setq result (kt:write-aircon-book records groups)))
  (kt:timed "Excel計算設定の復元" 'vlax-put-property (list kt:excel 'Calculation calculation))
  (vlax-invoke-method kt:excel 'CalculateFull)
  (if (= (kt:cfg 'category) "KANKI") (progn (kc:verify) (kc:verify-errors kc:baseline)))
  result)
(defun kt:show-warnings (/ s)
  (princ (strcat "\n警告：" (itoa (length kt:warnings)) "件"))
  (foreach s (reverse kt:warnings) (princ (strcat "\n・" s))))

;; 最後に選択した案件Excelを、再ロード・AutoCAD再起動後も保持する。
(defun kt:excel-dialog-default (/ previous folder)
  (setq previous (getenv "PIPEAUTOCAD_KIKITABLE_LAST_EXCEL"))
  (cond
    ((and previous (/= previous "") (findfile previous)) previous)
    ((and previous (/= previous "")
          (setq folder (vl-filename-directory previous))
          (vl-file-directory-p folder))
      (strcat folder "\\"))
    (T (getvar "DWGPREFIX"))))
(defun kt:select-excel ()
  ;; xlsmを先頭（初期フィルター）にし、xlsxも選択可能にする。
  ;; bit4で、選択した別拡張子へ既定拡張子が付加されるのを防ぐ。
  (getfiled "機器表を更新する案件Excelを選択してください。"
    (kt:excel-dialog-default) "xlsm;xlsx" 4))

;; -------- エントリーポイント：図面は読取り専用、Excel保存は全書込み後 --------
(defun c:KIKITABLE (/ *error* kt:objects kt:excel kt:book kt:reason kt:stage kt:log-path
                      kt:config kt:tags category kc:summary kc:verify-sheet kc:verify-end kc:baseline kc:row-shifts
                      kt:cell-context kt:warnings kt:raw-tags kt:plan records groups path ext saved saving)
  (defun *error* (msg)
    (kt:trace (strcat "ERROR " (if kt:stage kt:stage "") " / " (if msg msg "")))
    (princ (strcat "\nKIKITABLE [" (if kt:stage kt:stage "開始") "]："
      (cond (kt:reason)
            ((and msg (wcmatch (strcase msg) "*CANCEL*,*QUIT*,*BREAK*")) "キャンセルしました。")
            (msg) (T "不明なエラー"))))
    (if kt:cell-context (princ (strcat "\n直前の書込みセル：" kt:cell-context)))
    (kt:cleanup)
    (cond (saved (princ "\nExcelは保存済みです。"))
          (saving (princ "\nExcel保存中にエラーが発生しました。対象Excelを確認してください。"))
          (T (princ "\nExcelへの保存は行っていません。")))
    (kt:show-warnings) (princ))
  (setq category (kt:category)
        kt:config (if (= category "KANKI") (append kt:vent-config kt:aircon-config) kt:aircon-config)
        kt:tags (if (= category "KANKI") kt:vent-tags kt:aircon-tags))
  (setq kt:log-path (vl-filename-mktemp "KIKITABLE-diagnostic-" (getenv "TEMP") ".log"))
  (princ (strcat "\nKIKITABLE Version: " kt:version " / ログ：" kt:log-path))
  (kt:trace "START")
  (setq kt:stage "図面属性の収集" kt:raw-tags (kt:raw-columns) records (kt:collect))
  (if (null records)
    (princ (strcat "\n" (kt:cfg 'block) " ブロックが見つかりません。"))
    (progn
      (setq groups (kt:group records) kt:stage "Excelファイル選択")
      (setq path (kt:select-excel))
      (kt:trace "00 選択画面から復帰・ファイル存在確認")
      (if path
        (progn
          (if (not (findfile path)) (kt:fail "Excelファイルが存在しません。"))
          (setq ext (strcase (vl-filename-extension path)))
          (if (not (member ext '(".XLSX" ".XLSM"))) (kt:fail ".xlsx または .xlsm を選択してください。"))
          (setenv "PIPEAUTOCAD_KIKITABLE_LAST_EXCEL" path)
          (setq kt:stage "案件Excelを開く") (kt:open path)
          (kt:trace "09 見出し・集計・帳票書込み開始")
          (setq kt:stage "見出し・集計の確認") (kt:write-book records groups)
          (kt:trace "10 帳票書込み完了・保存開始")
          (setq kt:stage "Excel保存" kt:cell-context nil saving T)
          (vlax-invoke-method kt:book 'Save)
          (if (/= (kt:unwrap (vlax-get-property kt:book 'Saved)) :vlax-true)
            (kt:fail "Excelの保存完了を確認できませんでした。"))
          (setq saved T) (kt:trace "11 保存完了・Excel終了開始") (kt:cleanup)
          (kt:trace "12 Excel終了完了")
          (princ (strcat "\nKIKITABLE 更新完了\n対象Excel：\n" path
            "\nCADブロック数：" (itoa (length records)) "\n機器種類数：" (itoa (length groups))
            "\n" (kt:cfg 'raw-sheet) "：更新\n" (kt:cfg 'sheet) "：更新"))
          (if (= category "KANKI") (princ kc:summary))
          (kt:show-warnings))
        (princ "\nキャンセルしました。"))))
  (kt:cleanup) (princ))

;; KIKITABLE L4: room calculations. No independent Save/Quit in these helpers.
;; All mutations belong to the caller's dedicated, unsaved Excel transaction.
(vl-load-com)
(setq kc:sheet-name "換気計算(一般）" kc:settings-name "KANKI_部屋設定"
      kc:equipment-name "KANKI_機器用途" kc:archive-name "KANKI_旧設定")
(defun kc:text (v) (cond ((null v) "") ((= (type v) 'STR) v)
  ((numberp v) (if (= v (fix v)) (itoa (fix v)) (vl-princ-to-string v))) (T "")))
(defun kc:positive (s / n) (if (and (setq n (kt:number (kc:text s))) (> n 0)) n))
(defun kc:unique (items / out item)
  (foreach item items (if (not (member item out)) (setq out (append out (list item))))) out)
(defun kc:error-count (ws area / value)
  ;; VT_ERROR cannot be marshalled by some AutoLISP/Excel versions. Evaluate
  ;; ISERROR inside Excel instead of converting an array containing VT_ERROR.
  (setq value (kt:unwrap (vlax-invoke-method ws 'Evaluate
    (strcat "SUMPRODUCT(--ISERROR(" (vlax-get-property area 'Address :vlax-true :vlax-true 1 :vlax-false (vlax-make-variant)) "))"))))
  (if (not (numberp value)) (kt:fail "Excelエラー件数を検証できません。")) value)
(defun kc:errors (/ sheets ws area found cells cell result name count actual kind)
  ;; Inspect only error cells through their text, never marshal their Value2.
  (setq sheets (kt:own (vlax-get-property kt:book 'Worksheets)))
  (vlax-for ws sheets
    (kt:own ws)
    (setq name (vlax-get-property ws 'Name) area (kt:own (vlax-get-property ws 'UsedRange))
      count (kc:error-count ws area) actual 0)
    (if (> count 0)
      (foreach kind '(-4123 2)
        (setq found (vl-catch-all-apply 'vlax-invoke-method (list area 'SpecialCells kind 16)))
        (if (not (vl-catch-all-error-p found))
          (progn
            (setq found (kt:own found) cells (kt:own (vlax-get-property found 'Cells)))
            (vlax-for cell cells
              (kt:own cell)
              (setq result (cons (list name (vlax-get-property cell 'Row) (vlax-get-property cell 'Column)
                (vlax-get-property cell 'Text)) result) actual (1+ actual))
              (kt:drop cell))
            (kt:drop cells) (kt:drop found)))))
    (if (/= count actual) (kt:fail (strcat name "のExcelエラー位置を照合できません。")))
    (kt:drop area)
    (kt:drop ws))
  (kt:drop sheets) result)
(defun kc:verify-errors (baseline / expected old shift after e)
  (foreach old baseline
    (foreach shift (reverse kc:row-shifts)
      (if (and (= (car old) (car shift)) (> (cadr old) (cadr shift)))
        (setq old (list (car old) (+ (cadr old) (caddr shift)) (caddr old) (cadddr old)))))
    (setq expected (cons old expected)))
  (setq after (kc:errors))
  (foreach e after
    (if (not (member e expected))
      (kt:fail (strcat "更新後に新しいExcelエラー：" (car e) "!" (kt:address (cadr e) (caddr e)) "。保存せず中止。")))))
(defun kc:excel-floor (v / s)
  ;; Only the existing Excel display accepts fullwidth digits / F. CAD uses kt:floor.
  (setq s (strcase (kt:trim (vl-string-translate "０１２３４５６７８９Ｆｆ" "0123456789FF" (kc:text v)))))
  (if (and (> (strlen s) 0) (= (substr s (strlen s)) "F")) (setq s (substr s 1 (1- (strlen s)))))
  (kt:floor s))
(defun kc:key (record / f n)
  (setq f (kt:floor (kt:get record "FLOOR")) n (kt:trim (kt:get record "LOCATION")))
  (if (and f (/= n "")) (list f n)))
(defun kc:label (key) (strcat (car key) "F / " (cadr key)))
(defun kc:less (a b)
  (if (= (caar a) (caar b)) (kt:natural-less (cadar a) (cadar b))
    (kt:natural-less (caar a) (caar b))))
(defun kc:rooms (records / groups r k g)
  (foreach r records
    (if (setq k (kc:key r))
      (if (setq g (assoc k groups))
        (setq groups (subst (cons k (append (cdr g) (list r))) g groups))
        (setq groups (cons (list k r) groups)))
      (kt:warn (strcat "部屋集計対象外：FLOOR=" (kt:get r "FLOOR") " / LOCATION="
        (kt:get r "LOCATION") " / Handle=" (kt:get r "HANDLE") "：階・室名が不足または不正。生データに保持。"))))
  (vl-sort groups 'kc:less))
(defun kc:dimension (records tag / values missing bad r s n)
  ;; Return (value issue). Missing on some instances is a warning, not a conflict.
  (foreach r records
    (setq s (kt:trim (kt:get r tag)) n (kc:positive s))
    (cond ((= s "") (setq missing T))
          ((null n) (setq bad T))
          ((not (member n values)) (setq values (cons n values)))))
  (cond ((or bad (> (length values) 1)) (list "" (strcat tag "不正値/矛盾")))
        ((null values) (list "" (strcat tag "未入力")))
        (missing (list (car values) (strcat tag "一部未入力")))
        (T (list (car values) ""))))
(defun kc:read (ws r1 c1 r2 c2 / area result)
  (setq area (kt:range ws r1 c1 r2 c2)
        result (kt:array (vlax-get-property area 'Value2)))
  (kt:drop area)
  (mapcar '(lambda (row) (mapcar 'kt:unwrap row)) result))
(defun kc:no-errors (ws r1 c1 r2 c2 / area count)
  (setq area (kt:range ws r1 c1 r2 c2) count (kc:error-count ws area))
  (kt:drop area)
  (if (> count 0)
      (kt:fail (strcat "換気計算の対象範囲にExcelエラーがあります："
        (kt:address r1 c1) "～" (kt:address r2 c2) "。元の手入力・参照式を修正して再実行してください。"))))
(defun kc:unprotected (ws /)
  (if (= (kt:unwrap (vlax-get-property ws 'ProtectContents)) :vlax-true)
    (kt:fail (strcat (vlax-get-property ws 'Name) "は保護されています。保存せず中止。"))))
(defun kc:plain (ws r1 c1 r2 c2 / area merged)
  (kc:unprotected ws)
  (setq area (kt:range ws r1 c1 r2 c2) merged (kt:unwrap (vlax-get-property area 'MergeCells)))
  (kt:drop area)
  (if (not (equal merged :vlax-false)) (kt:fail "換気計算の明細/設定領域に未対応の結合セルがあります。")))
(defun kc:get-sheet (sheets name headers / ws area font columns)
  (setq ws (kt:sheet sheets name))
  (if ws
    (progn
      (kc:plain ws 1 1 (max 2 (kt:last ws 'Row)) (length headers))
      (kc:no-errors ws 1 1 (max 2 (kt:last ws 'Row)) (length headers))
      (if (not (equal (car (kc:read ws 1 1 1 (length headers))) headers))
        (kt:fail (strcat name "の構造が一致しません。専用シート名の衝突を確認してください。"))))
    (progn (setq ws (kt:own (vlax-invoke-method sheets 'Add)))
      (vlax-put-property ws 'Name name) (kt:put-matrix ws 1 1 (list headers))
      (setq area (kt:range ws 1 1 1 (length headers))
        font (kt:own (vlax-get-property area 'Font)) columns (kt:own (vlax-get-property area 'Columns)))
      (vlax-put-property font 'Bold :vlax-true)
      (vlax-invoke-method columns 'AutoFit)
      (kt:drop columns) (kt:drop font) (kt:drop area)
      (if (= name kc:settings-name)
        (kt:put-matrix ws 1 13 '(("C:Eは 適用 / 対象外 / 未設定")
          ("Fは 単室 / 複数室 / 対象外 / 未設定") ("Gは正の丸め単位、Hは 四捨五入 / 切り上げ")
          ("H,I,J,L,N,Q列の条件は換気計算表に入力") ("I:KはCADから更新。構成・機器用途変更後はKIKITABLEを再実行。"))))
      (if (= name kc:equipment-name)
        (kt:put-matrix ws 1 7 '(("Dは 排気 / 給気 / 対象外 / 未設定")
          ("Eは 単室 / 複数室 / 対象外 / 未設定") ("SYSTEM・NUM・MODELの組ごとに担当用途を確認して入力。変更後はKIKITABLEを再実行。"))))))
  ws)
(setq kc:setting-headers '("階" "室名" "人員法" "シックハウス" "換気回数法" "担当構成" "丸め単位" "丸め方法" "CAD要確認" "Handle" "静圧内訳"))
(setq kc:equipment-headers '("SYSTEM" "NUM" "MODEL" "給排気区分" "担当構成"))
(defun kc:end (ws / setup text area areas rows cols end o)
  ;; Print boundary is the explicit initial managed detail region, never UsedRange.
  (kc:unprotected ws)
  (setq setup (kt:own (vlax-get-property ws 'PageSetup)) text (vlax-get-property setup 'PrintArea))
  (if (= text "") (kt:fail "換気計算表の印刷範囲C3:V最終行が必要です。"))
  (setq area (kt:own (vlax-get-property ws 'Range text))
        areas (kt:own (vlax-get-property area 'Areas))
        rows (kt:own (vlax-get-property area 'Rows)) cols (kt:own (vlax-get-property area 'Columns)))
  (if (or (/= 1 (vlax-get-property areas 'Count)) (/= 3 (vlax-get-property area 'Row))
          (/= 3 (vlax-get-property area 'Column)) (/= 20 (vlax-get-property cols 'Count)))
    (kt:fail "換気計算表の印刷範囲は連続したC3:V最終行にしてください。"))
  (setq end (+ 2 (vlax-get-property rows 'Count)))
  (foreach o (list cols rows areas area setup) (kt:drop o))
  (if (< end 6) (kt:fail "換気計算表の明細領域がありません。"))
  (kc:plain ws 6 3 end 22)
  end)
(defun kc:headers (ws / checks check)
  ;; Top-left cells of reference's merged, three-row header.
  (setq checks '((3 3 "階") (3 4 "室名") (3 5 "床面積") (3 6 "天井高さ")
    (3 7 "容積") (3 8 "人員") (3 9 "占有面積") (3 10 "人員による換気量") (4 10 "一人当たり")
    (4 11 "換気量") (3 14 "換気回数法") (4 18 "風量") (4 19 "静圧")
    (3 12 "シックハウス/法２８条\n換気計算") (3 16 "決定\n換気量")
    (3 17 "換気方式") (3 18 "採用機器の換気能力") (3 22 "送風機\n形式")
    (3 20 "判定") (3 21 "機器番号")))
  (foreach check checks
    (if (/= (kc:text (kt:cell-value ws (car check) (cadr check))) (caddr check))
      (kt:fail (strcat "換気計算表の見出し不一致：" (kt:address (car check) (cadr check)))))))
(defun kc:target (sheets / ws path books template template-sheets source)
  (setq ws (kt:sheet sheets kc:sheet-name))
  (if (null ws)
    (progn
      (setq path (getenv "PIPEAUTOCAD_KANKI_TEMPLATE"))
      (if (or (null path) (= path ""))
        (setq path (cond ((findfile "換気計算テンプレート.xlsx"))
          ((and (boundp 'pa-path) pa-path) (strcat pa-path "/換気計算テンプレート.xlsx")))))
      (if (not (findfile path)) (kt:fail "検証済み換気計算テンプレートがありません。PIPEAUTOCAD_KANKI_TEMPLATEを設定してください。"))
      (setq kt:stage "換気計算テンプレート読込") (kt:trace "換気計算テンプレートを読み取り専用で開く")
      (setq books (kt:own (vlax-get-property kt:excel 'Workbooks))
        template (kt:own (vlax-invoke-method books 'Open path 0 :vlax-true 5 "" "" :vlax-true 2 "" :vlax-false :vlax-false))
        template-sheets (kt:own (vlax-get-property template 'Worksheets))
        source (kt:own (vlax-get-property template-sheets 'Item kc:sheet-name)))
      (kc:headers source) (kc:end source)
      ;; Excel's native sheet Copy preserves page setup, widths and header merges.
      (vlax-invoke-method source 'Copy (kt:own (vlax-get-property sheets 'Item 1)))
      (kt:drop source) (kt:drop template-sheets)
      (vlax-invoke-method template 'Close :vlax-false)
      (kt:drop template)
      (kt:trace "換気計算テンプレートのコピー完了")
      (setq ws (kt:sheet sheets kc:sheet-name))
      (if (null ws) (kt:fail "換気計算テンプレートをコピーできません。"))))
  (kc:headers ws) ws)
(defun kc:old (ws end / rows row f n key out inputs c)
  ;; Manual inputs are captured as evaluated values, before rows move.
  ;; A formula pointing at a row must not silently follow a different room.
  (foreach c '(8 9 10 12 14 17) (kc:no-errors ws 6 c end c))
  (setq rows (kc:read ws 6 3 end 22))
  (foreach row rows
    (setq f (kc:excel-floor (car row)) n (kt:trim (kc:text (cadr row))))
    (if (or f (/= n ""))
      (progn
        (if (or (null f) (= n "")) (kt:fail "換気計算表の明細に階・室名が片方だけの行があります。"))
        (setq key (list f n))
        (if (assoc key out) (kt:fail (strcat "換気計算表の部屋キー重複：" (kc:label key))))
        (setq inputs (mapcar '(lambda (i) (nth i row)) '(5 6 7 9 11 14)))
        (setq out (cons (list key inputs row) out)))))
  out)
(defun kc:settings (ws / rows out row key)
  (if (> (kt:last ws 'Row) 1)
    (foreach row (kc:read ws 2 1 (kt:last ws 'Row) 11)
      (if (/= (kc:text (cadr row)) "")
        (progn
          (setq key (list (kc:excel-floor (car row)) (kt:trim (kc:text (cadr row)))))
          (if (or (null (car key)) (assoc key out)) (kt:fail "部屋設定の階が不正、または部屋キーが重複しています。"))
          (setq out (cons (cons key (cddr row)) out))))))
  out)
(defun kc:uses (ws records / rows out row key r)
  (if (> (kt:last ws 'Row) 1)
    (setq rows (kc:read ws 2 1 (kt:last ws 'Row) 5)))
  (foreach row rows
    (if (/= (kc:text (car row)) "")
      (progn
        (setq key (mapcar 'kc:text (list (car row) (cadr row) (caddr row))))
        (if (assoc key out) (kt:fail "機器用途のSYSTEM・NUM・MODELが重複しています。"))
        (setq out (cons (cons key (cdddr row)) out)))))
  (foreach r records
    (setq key (list (kt:trim (kt:get r "SYSTEM")) (kt:trim (kt:get r "NUM")) (kt:trim (kt:get r "MODEL"))))
    (if (not (assoc key out)) (setq out (append out (list (cons key '("未設定" "未設定")))))))
  (kt:put-matrix ws 2 1 (mapcar '(lambda (entry) (append (car entry) (cdr entry))) out))
  out)
(defun kc:capacity (records uses / sum valid directions r setting n p pressures labels counts pair key types reasons)
  (setq sum 0 valid T)
  (foreach r records
    (setq key (list (kt:trim (kt:get r "SYSTEM")) (kt:trim (kt:get r "NUM")) (kt:trim (kt:get r "MODEL")))
      setting (cdr (assoc key uses)) n (kc:positive (kt:get r "AIRFLOW"))
      p (kt:number (kt:get r "STATIC_PRESSURE")))
    (if (not (member (car setting) '("排気" "給気"))) (setq reasons (cons "機器の給排気区分が未設定/対象外" reasons)))
    (if (/= (cadr setting) "単室") (setq reasons (cons "機器の担当構成が単室でない" reasons)))
    (if (= (kt:get r "EQUIP_TYPE") "全熱交換器") (setq reasons (cons "全熱交換器は自動判定対象外" reasons)))
    (if (null (kt:identity r)) (setq reasons (cons "SYSTEM/NUM不足" reasons)))
    (if (= (kt:trim (kt:get r "MODEL")) "") (setq reasons (cons "MODEL不足" reasons)))
    (if (null n) (setq reasons (cons "AIRFLOW欠損/不正" reasons)))
    (if (null p) (setq reasons (cons "STATIC_PRESSURE欠損/不正" reasons)))
    (if n (setq sum (+ sum n)))
    (if (not (member (car setting) directions)) (setq directions (cons (car setting) directions)))
    (if (not (member p pressures)) (setq pressures (cons p pressures)))
    (setq labels (append labels (list (strcat (kt:key r) "=" (kt:get r "STATIC_PRESSURE") "Pa / " (kc:text (car setting))))))
    (setq key (kt:key r) pair (assoc key counts))
    (if pair (setq counts (subst (cons key (1+ (cdr pair))) pair counts))
      (setq counts (append counts (list (cons key 1)))))
    (if (not (member (kt:get r "TYPE") types)) (setq types (append types (list (kt:get r "TYPE"))))))
  (if (/= (length directions) 1) (setq reasons (cons "給排気区分が混在" reasons)))
  (if (/= (length pressures) 1) (setq reasons (cons "静圧が不一致" reasons)))
  (setq reasons (vl-remove-if '(lambda (s) (= s "")) reasons) valid (null reasons))
  (list (if valid sum "") (if (and (= (length pressures) 1) (car pressures)) (car pressures) "")
    (kt:join (mapcar '(lambda (p) (strcat (car p) (if (> (cdr p) 1) (strcat "×" (itoa (cdr p)) "台") ""))) counts) " / ")
    (kt:join types " / ") (kt:join (kc:unique (reverse reasons)) "; ") (kt:join labels " / ")))
(defun kc:formulas (row setting-row / r s cfg g k m o p texpr valid states unit rounding pair)
  (setq r (itoa row) s (itoa setting-row) cfg (strcat "'" kc:settings-name "'!")
    g (strcat "=IF(AND(ISNUMBER(E" r "),E" r ">0,ISNUMBER(F" r "),F" r ">0),E" r "*F" r ",\"\")")
    k (strcat "=IF(AND(" cfg "C" s "=\"適用\",ISNUMBER(H" r "),H" r ">=0,ISNUMBER(J" r "),J" r ">0),H" r "*J" r ",\"\")")
    m (strcat "=IF(AND(" cfg "D" s "=\"適用\",ISNUMBER(G" r "),ISNUMBER(L" r "),L" r ">0),G" r "*L" r ",\"\")")
    unit (strcat cfg "G" s) rounding (strcat cfg "H" s)
    o (strcat "=IF(AND(" cfg "E" s "=\"適用\",ISNUMBER(G" r "),ISNUMBER(N" r "),N" r ">0,ISNUMBER(" unit ")," unit ">0,OR(" rounding "=\"四捨五入\"," rounding "=\"切り上げ\")),IF(" rounding "=\"切り上げ\",ROUNDUP(G" r "*N" r "/" unit ",0),ROUND(G" r "*N" r "/" unit ",0))*" unit ",\"\")"))
  (setq states nil)
  (foreach pair '(("C" . "K") ("D" . "M") ("E" . "O"))
    (setq states (append states (list (strcat "OR(" cfg (car pair) s "=\"対象外\",AND(" cfg (car pair) s "=\"適用\",ISNUMBER(" (cdr pair) r ")))")))))
  (setq valid (strcat "AND(" (kt:join states ",") ",OR(" cfg "C" s "=\"適用\"," cfg "D" s "=\"適用\"," cfg "E" s "=\"適用\"))")
    p (strcat "=IF(" valid ",MAX(K" r ",M" r ",O" r "),\"\")")
    texpr (strcat "=IF(OR(" cfg "I" s "<>\"\",AND(" cfg "F" s "<>\"未設定\"," cfg "F" s "<>\"単室\")),\"要確認\",IF(AND(" cfg "F" s "=\"単室\",ISNUMBER(E" r "),E" r ">0,ISNUMBER(F" r "),F" r ">0,ISNUMBER(P" r "),ISNUMBER(R" r "),ISNUMBER(S" r "),OR(Q" r "=1,Q" r "=2,Q" r "=3)),IF(R" r ">=P" r ",\"○\",\"×\"),\"要設定\"))"))
  (list (cons 7 g) (cons 11 k) (cons 13 m) (cons 15 o) (cons 16 p) (cons 20 texpr)))
(defun kc:formula-column (ws col rows / area array)
  (setq array (vlax-make-safearray vlax-vbVariant (cons 1 (length rows)) '(1 . 1)))
  (vlax-safearray-fill array (mapcar '(lambda (x) (list x)) rows))
  (setq area (kt:range ws 6 col (+ 5 (length rows)) col))
  (vlax-put-property area 'Formula (vlax-make-variant array)) (kt:drop area))
(defun kc:archive (sheets old settings rooms / ws rows entry setting row)
  (foreach entry old
    (if (not (assoc (car entry) rooms))
      (progn
        (setq setting (cdr (assoc (car entry) settings)))
        (setq rows (append rows (list (append (list (rtos (getvar "DATE") 2 8) (kc:label (car entry)))
          (caddr entry) (if setting (list (nth 0 setting) (nth 1 setting) (nth 2 setting) (nth 3 setting) (nth 4 setting) (nth 5 setting)) '("未設定" "未設定" "未設定" "未設定" 10 "四捨五入"))))))
        (kt:warn (strcat "削除された部屋：" (kc:label (car entry)) "。旧手入力はKANKI_旧設定に退避。")))))
  ;; Settings without a corresponding table row must also be recoverable.
  (foreach entry settings
    (if (and (not (assoc (car entry) rooms)) (not (assoc (car entry) old)))
      (progn
        (setq rows (append rows (list (append (list (rtos (getvar "DATE") 2 8) (kc:label (car entry)))
          '("" "" "" "" "" "" "" "" "" "" "" "" "" "" "" "" "" "" "" "") (list (nth 1 entry) (nth 2 entry) (nth 3 entry) (nth 4 entry) (nth 5 entry) (nth 6 entry))))))
        (kt:warn (strcat "出力外の旧部屋設定：" (kc:label (car entry)) "を退避。")))))
  (if rows
    (progn
      (setq ws (kc:get-sheet sheets kc:archive-name (append '("退避日時(JD)" "部屋キー")
        '("階" "室名" "床面積" "高さ" "容積" "人員" "占有面積" "一人当たり" "人員換気量" "SH回数" "SH換気量" "換気回数" "回数換気量" "決定換気量" "換気方式" "風量" "静圧" "判定" "機器番号" "形式")
        '("人員法状態" "SH状態" "回数法状態" "担当構成" "丸め単位" "丸め方法"))))
      (kt:put-matrix ws (1+ (kt:last ws 'Row)) 1 rows))))
(defun kc:extend (ws oldend newend / area source dest setup)
  (if (> newend oldend)
    (progn
      ;; Entire rows preserve bottom notes, right formulas, and external references.
      (setq area (kt:own (vlax-get-property ws 'Range (strcat (itoa (1+ oldend)) ":" (itoa newend)))))
      (setq kc:row-shifts (cons (list (vlax-get-property ws 'Name) oldend (- newend oldend)) kc:row-shifts))
      (vlax-invoke-method area 'Insert -4121) (kt:drop area)
      (setq source (kt:range ws oldend 3 oldend 22) dest (kt:range ws (1+ oldend) 3 newend 22))
      (vlax-invoke-method source 'Copy dest)
      (vlax-put-property dest 'RowHeight (vlax-get-property source 'RowHeight))
      (kt:drop dest) (kt:drop source)
      (setq setup (kt:own (vlax-get-property ws 'PageSetup)))
      (vlax-put-property setup 'PrintArea (strcat "$C$3:$V$" (itoa newend))) (kt:drop setup))))
(defun kc:write (records / sheets ws config eq oldend end old settings uses rooms matrix configrows formulas
    room key instances input state area height capacity issues handles row sr missing dim item c)
  (setq sheets (kt:own (vlax-get-property kt:book 'Worksheets)) ws (kc:target sheets)
    oldend (kc:end ws) old (kc:old ws oldend)
    config (kc:get-sheet sheets kc:settings-name kc:setting-headers)
    eq (kc:get-sheet sheets kc:equipment-name kc:equipment-headers)
    settings (kc:settings config) uses (kc:uses eq records) rooms (kc:rooms records)
    end (max oldend (+ 5 (length rooms))))
  (if (null rooms) (kt:fail "有効なFLOOR＋LOCATIONが0室です。既存計算表は更新せず中止します。"))
  (kc:archive sheets old settings rooms)
  (kc:extend ws oldend end)
  (kc:plain ws 6 3 end 22)
  (setq row 6 sr 2)
  (foreach room rooms
    (setq key (car room) instances (cdr room)
      input (cadr (assoc key old)) state (cdr (assoc key settings))
      area (kc:dimension instances "FLOOR_AREA") height (kc:dimension instances "CEILING_HEIGHT")
      capacity (kc:capacity instances uses)
      issues (nth 4 capacity)
      handles (kt:join (mapcar '(lambda (r) (kt:get r "HANDLE")) instances) ","))
    (if (null input) (setq input '("" "" "" "" "" "")))
    (if (null state) (setq state '("未設定" "未設定" "未設定" "未設定" 10 "四捨五入")))
    (foreach dim (list area height)
      (if (/= (cadr dim) "")
        (progn
          (kt:warn (strcat (kc:label key) " / Handle=" handles "：" (cadr dim)))
          (if (wcmatch (cadr dim) "*不正*,*矛盾*") (setq issues (kt:join (list issues (cadr dim)) "; "))))))
    (if (/= issues "") (kt:warn (strcat (kc:label key) " / Handle=" handles "：" issues " / " (nth 5 capacity))))
    (setq matrix (append matrix (list (list (strcat (car key) "F") (cadr key) (car area) (car height) ""
      (nth 0 input) (nth 1 input) (nth 2 input) "" (nth 3 input) "" (nth 4 input) "" "" (nth 5 input)
      (nth 0 capacity) (nth 1 capacity) "" (nth 2 capacity) (nth 3 capacity)))))
    (setq configrows (append configrows (list (append (list (car key) (cadr key))
      (list (nth 0 state) (nth 1 state) (nth 2 state) (nth 3 state) (nth 4 state) (nth 5 state))
      (list issues handles (nth 5 capacity))))))
    (setq formulas (append formulas (list (kc:formulas row sr))) row (1+ row) sr (1+ sr)))
  ;; Clear only the explicitly managed rectangle. A:B and W onward survive.
  (kt:clear ws 6 3 end 22)
  (kt:clear config 2 1 (max 2 (kt:last config 'Row)) 11)
  (if matrix
    (progn
      (kt:put-matrix ws 6 3 matrix) (kt:put-matrix config 2 1 configrows)
      (foreach c '(7 11 13 15 16 20)
        (kc:formula-column ws c (mapcar '(lambda (r) (cdr (assoc c r))) formulas)))))
  (setq kc:verify-sheet ws kc:verify-end (+ 5 (length rooms))
    kc:summary (strcat "\n" kc:sheet-name "：更新\n換気計算表の部屋数：" (itoa (length rooms))))
  (if (= (length rooms) 0) (kt:warn "有効な部屋キーが0件のため、全旧部屋の設定を退避しました。")))
(defun kc:verify (/ rows row counts status p r)
  (setq counts '(("○" . 0) ("×" . 0) ("要設定" . 0) ("要確認" . 0)))
  (if (>= kc:verify-end 6)
    (progn
      (kc:no-errors kc:verify-sheet 6 3 kc:verify-end 22)
      (setq rows (kc:read kc:verify-sheet 6 16 kc:verify-end 20))
      (foreach row rows
        (setq status (nth 4 row) p (assoc status counts))
        (if (null p) (kt:fail "換気計算表の判定値が不正です。"))
        (if (and (= status "○") (or (not (numberp (car row))) (not (numberp (nth 2 row)))
          (< (nth 2 row) (car row)))) (kt:fail "換気計算表の正常判定と能力比較が一致しません。"))
        (setq counts (subst (cons status (1+ (cdr p))) p counts)))))
  (setq kc:summary (strcat kc:summary "\n正常判定：" (itoa (cdr (assoc "○" counts)))
    " / 能力不足：" (itoa (cdr (assoc "×" counts))) " / 要設定：" (itoa (cdr (assoc "要設定" counts)))
    " / 要確認：" (itoa (cdr (assoc "要確認" counts))))))

;; Explicit installation command. Never called by KIKITABLE or KIKISET.
;; ATTSYNC can replace AttributeReference objects; reacquire by INSERT Handle.
(defun kc:attr-text (obj / attrs data a)
  (setq attrs (append (kt:attribute-objects obj 'GetAttributes) (kt:attribute-objects obj 'GetConstantAttributes)))
  (foreach a attrs (setq data (cons (cons (strcase (vla-get-TagString a)) (vla-get-TextString a)) data))) data)
(defun c:KANKIROOMATTR (/ *error* doc blocks definition obj att names snapshots entry attrs a tag old
    kt:objects kt:warnings kt:raw-tags kt:config undo begun)
  (defun *error* (msg)
    (foreach obj kt:objects (vl-catch-all-apply 'vlax-release-object (list obj)))
    (setq kt:objects nil)
    (if begun (progn (vla-EndUndoMark doc) (command-s "_.U")))
    (if doc (vl-catch-all-apply 'vlax-release-object (list doc)))
    (princ (strcat "\nKANKIROOMATTR：中止し、変更を取り消しました。" (if msg msg ""))) (princ))
  (setq doc (vla-get-ActiveDocument (vlax-get-acad-object))
    blocks (kt:own (vla-get-Blocks doc))
    definition (vl-catch-all-apply 'vla-Item (list blocks "KANKI_KIKI")))
  (if (vl-catch-all-error-p definition) (kt:fail "この図面にKANKI_KIKIの定義がありません。"))
  (setq definition (kt:own definition))
  (if (= (vla-get-IsXRef definition) :vlax-true) (kt:fail "外部参照の定義は変更できません。"))
  (setq kt:config '((block . "KANKI_KIKI")) kt:raw-tags nil)
  ;; Retain every original tag, including equipment and nonstandard attributes.
  (vlax-for obj blocks
    (if (/= (vla-get-IsXRef obj) :vlax-true)
      (vlax-for old obj
        (if (and (= (vla-get-ObjectName old) "AcDbBlockReference")
          (= (strcase (if (vlax-property-available-p old 'EffectiveName) (vla-get-EffectiveName old) (vla-get-Name old))) "KANKI_KIKI"))
          (setq snapshots (cons (cons (vla-get-Handle old) (kc:attr-text old)) snapshots))))))
  (vlax-for obj definition
    (if (= (vla-get-ObjectName obj) "AcDbAttributeDefinition") (setq names (cons (strcase (vla-get-TagString obj)) names))))
  (vla-StartUndoMark doc) (setq begun T)
  (foreach entry '(("FLOOR_AREA" . "床面積(㎡)：単位なし、正数") ("CEILING_HEIGHT" . "天井高さ(m)：単位なし、正数"))
    (if (not (member (car entry) names))
      (kt:own (vla-AddAttribute definition 2.5 1 (cdr entry) (vlax-3d-point '(0.0 0.0 0.0)) (car entry) ""))))
  (command "_.ATTSYNC" "_Name" "KANKI_KIKI")
  (foreach entry snapshots
    (if (null (handent (car entry))) (kt:fail "属性反映後に元のブロックを取得できません。"))
    (setq obj (kt:own (vlax-ename->vla-object (handent (car entry)))) attrs (kt:attribute-objects obj 'GetAttributes))
    (foreach a attrs
      (setq tag (strcase (vla-get-TagString a)) old (assoc tag (cdr entry)))
      (if old (vla-put-TextString a (cdr old))))
    (setq names (kc:attr-text obj))
    (foreach old (cdr entry)
      (if (not (equal (cdr old) (cdr (assoc (car old) names))))
        (kt:fail (strcat "既存属性の保持を確認できません：" (car entry) " / " (car old)))))
    (if (or (not (assoc "FLOOR_AREA" names)) (not (assoc "CEILING_HEIGHT" names)))
      (kt:fail "新属性の反映を確認できません。")))
  (vla-EndUndoMark doc) (setq begun nil)
  (foreach obj kt:objects (vl-catch-all-apply 'vlax-release-object (list obj)))
  (vlax-release-object doc)
  (princ (strcat "\nKANKIROOMATTR：定義と既存配置" (itoa (length snapshots)) "台へ属性を反映。既存値を照合しました。DWGは未保存です。"))
  (princ))
(princ)
(princ (strcat "\nKIKITABLE L4（換気計算表対応）loaded. Version: " kt:version " / Command: KIKITABLE"))
(princ)
