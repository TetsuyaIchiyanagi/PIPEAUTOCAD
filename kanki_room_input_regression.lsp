;; Isolated AutoCAD only. ki:fixture must be a disposable ver03 workbook copy.
(setq ki:count 0)
(defun *error* (msg) (princ (strcat "\nROOM_INPUT_ERROR: " msg)) (kt:cleanup) (princ))
(defun ki:assert (ok label)
  (if (not ok) (progn (princ (strcat "\nFAIL: " label)) (kt:cleanup) (exit)))
  (setq ki:count (1+ ki:count)) (princ (strcat "\nPASS: " label)))
(setq ki:fields '(("HUMAN" . "1") ("KANKIRYOU" . "30") ("KANKIKAISUU" . "2")
  ("CICKHOUSE" . "0.3") ("KANKIHOUSIKI" . "3")))
(setq ki:old '(99.0 5.0 9.0 0.5 1.0 1.0 "KEEP-NOTE")
  ki:state '("未設定" "未設定" "未設定" "未設定" 10 "四捨五入"))
(setq ki:cad (kc:cad-inputs (list ki:fields ki:fields) ki:old ki:state))
(ki:assert (equal (car ki:cad) '(1.0 5.0 30.0 0.3 2.0 3.0 "KEEP-NOTE") 1e-8) "five-cad-fields-no-sum-preserve-occupancy-and-note")
(ki:assert (equal (list (nth 0 (cadr ki:cad)) (nth 1 (cadr ki:cad)) (nth 2 (cadr ki:cad))) '("適用" "適用" "適用")) "cad-conditions-enable-calculations")
(ki:assert (equal (car (kc:cad-inputs '(nil) ki:old ki:state)) ki:old) "missing-cad-retains-excel")
(ki:assert (equal (kc:cad-room-value (list '(("HUMAN" . "1")) '(("HUMAN" . "1.0"))) "HUMAN") '(1.0 "")) "numeric-equivalence")
(ki:assert (numberp (car (kc:cad-room-value (list ki:fields nil) "HUMAN"))) "partial-missing-adopts-present")
(ki:assert (= (car (kc:cad-room-value (list '(("HUMAN" . "1")) '(("HUMAN" . "2"))) "HUMAN")) "") "room-conflict-not-summed")
(foreach ki:bad '("-1" "abc" "1人")
  (ki:assert (= (car (kc:cad-room-value (list (list (cons "HUMAN" ki:bad))) "HUMAN")) "") "invalid-number-not-adopted"))
(ki:assert (= (car (kc:cad-room-value '((("KANKIHOUSIKI" . "4"))) "KANKIHOUSIKI")) "") "ventilation-mode-limited-to-1-2-3")
(setq ki:zero (kc:cad-inputs '((("HUMAN" . "0") ("KANKIRYOU" . "30") ("CICKHOUSE" . "0") ("KANKIKAISUU" . "0"))) ki:old ki:state))
(ki:assert (= (nth 0 (car ki:zero)) 0.0) "zero-occupants-retained")
(ki:assert (equal (list (nth 1 (cadr ki:zero)) (nth 2 (cadr ki:zero))) '("対象外" "対象外")) "zero-rates-disable-methods")
(foreach ki:dash '("-" "－" "−")
  (ki:assert (equal (kc:cad-room-value (list (list (cons "HUMAN" ki:dash))) "HUMAN") (list ki:dash "")) "dash-preserved-without-warning"))
(ki:assert (= (car (kc:cad-room-value (list '(("HUMAN" . "-")) '(("HUMAN" . "1"))) "HUMAN")) "") "dash-vs-number-is-room-conflict")
(ki:assert (equal (kc:cad-room-value '((("CIQKHOUSE" . "0.5"))) "CICKHOUSE") '(0.5 "")) "actual-ciqkhouse-tag-read")
(ki:assert (equal (kc:cad-room-value '((("CIQKHOUSE" . "0.50") ("CICKHOUSE" . "0.5"))) "CICKHOUSE") '(0.5 "")) "sick-house-aliases-agree")
(ki:assert (= (car (kc:cad-room-value '((("CIQKHOUSE" . "0.5") ("CICKHOUSE" . "0.3"))) "CICKHOUSE")) "") "sick-house-alias-conflict-refused")
(ki:assert (equal (kc:cad-room-value '((("CIQKHOUSE" . "-"))) "CICKHOUSE") '("-" "")) "ciqkhouse-dash-supported")
(ki:assert (= (kc:airflow (list '(("AIRFLOW" . "100")) '(("AIRFLOW" . "200")))) 300.0) "raw-airflow-without-purpose-settings")
(ki:assert (= (kc:airflow (list '(("AIRFLOW" . "100")) nil)) "") "missing-airflow-does-not-produce-partial-total")
(foreach ki:tag kt:room-input-tags
  (ki:assert (not (ks:writable-p ki:tag "99")) (strcat "kikiset-protect-" ki:tag)))
(setq kt:config (append kt:vent-config kt:aircon-config) kt:tags kt:vent-tags kt:raw-tags (kt:raw-columns))
(kt:open ki:fixture)
(setq ki:sheets (kt:own (vlax-get-property kt:book 'Worksheets)) ki:ws (kc:target ki:sheets) ki:end (kc:end ki:ws))
;; Fixture-only setup. Preserve an existing room's unrelated Excel inputs.
(kt:clear ki:ws 6 3 ki:end 22)
(kt:put-matrix ki:ws 6 3 '(("1F" "管理室" 6.3 2.4 "" 99 5 9 "" 0.5 "" 1 "" "" 1 "" 90 "" "EF-4" "KEEP-NOTE")))
(setq ki:r (append ki:fields '(("SYSTEM" . "EF") ("NUM" . "4") ("MODEL" . "VD-10ZVC7")
  ("MAKER" . "三菱電機") ("EQUIP_TYPE" . "ダクト用換気扇") ("TYPE" . "低騒音形")
  ("FLOOR" . "1") ("LOCATION" . "管理室") ("FLOOR_AREA" . "6.3") ("CEILING_HEIGHT" . "2.4")
  ("AIRFLOW" . "100") ("STATIC_PRESSURE" . "90") ("DUCT_DIA" . "100") ("HANDLE" . "TEST1"))))
(setq ki:r2 (subst '("HANDLE" . "TEST2") (assoc "HANDLE" ki:r) ki:r))
(kt:write-book (list ki:r ki:r2) (kt:group (list ki:r ki:r2)))
(setq ki:ws kc:verify-sheet)
(ki:assert (= (kt:cell-value ki:ws 6 18) 200.0) "excel-R-two-blocks-even-with-unconfigured-purpose")
(ki:assert (= (kt:cell-value ki:ws 6 20) "要確認") "airflow-display-does-not-bypass-judgement-checks")
(foreach ki:pair '((8 . 1.0) (10 . 30.0) (12 . 0.3) (14 . 2.0) (17 . 3.0) (9 . 5.0) (11 . 30.0) (13 . 4.536) (15 . 30.0) (16 . 30.0))
  (ki:assert (equal (kt:cell-value ki:ws 6 (car ki:pair)) (cdr ki:pair) 1e-7) (strcat "excel-" (kt:address 6 (car ki:pair)))))
(ki:assert (= (kt:cell-value ki:ws 6 22) "KEEP-NOTE") "legacy-remarks-preserved")
(ki:assert (= (kt:cell-value ki:ws 5 12) "回/h") "sick-house-header-does-not-claim-fixed-0.5")
(setq ki:dash-r (subst '("HUMAN" . "-") (assoc "HUMAN" ki:r) ki:r))
(setq ki:dash-r (subst '("KANKIRYOU" . "-") (assoc "KANKIRYOU" ki:dash-r) ki:dash-r))
(setq ki:dash-r (subst '("CICKHOUSE" . "-") (assoc "CICKHOUSE" ki:dash-r) ki:dash-r) kt:warnings nil)
(kt:write-book (list ki:dash-r) (kt:group (list ki:dash-r)))
(setq ki:ws kc:verify-sheet)
(foreach ki:column '(8 10 12)
  (ki:assert (= (kt:cell-value ki:ws 6 ki:column) "-") "excel-dash-preserved"))
(ki:assert (= (kt:cell-value ki:ws 6 11) "") "dash-person-method-not-calculated")
(ki:assert (= (kt:cell-value ki:ws 6 13) "") "dash-sick-house-method-not-calculated")
(ki:assert (= (kt:cell-value ki:ws 6 16) 30.0) "dash-does-not-block-active-air-change-method")
(ki:assert (not (vl-some '(lambda (message) (wcmatch message "*HUMAN不正*,*KANKIRYOU不正*,*CICKHOUSE不正*")) kt:warnings)) "dash-not-an-invalid-input-warning")
(setq ki:alias-r (cons '("CIQKHOUSE" . "0.5") (vl-remove-if '(lambda (entry) (= (car entry) "CICKHOUSE")) ki:dash-r)))
(kt:write-book (list ki:alias-r) (kt:group (list ki:alias-r)))
(setq ki:ws kc:verify-sheet)
(ki:assert (= (kt:cell-value ki:ws 6 12) 0.5) "excel-ciqkhouse-0.5-transferred")
(ki:assert (equal (kt:cell-value ki:ws 6 13) 7.56 1e-7) "excel-ciqkhouse-calculates-required-airflow")
(ki:assert (= (kt:cell-value (kt:sheet ki:sheets kc:settings-name) 2 4) "適用") "ciqkhouse-method-enabled")
(ki:assert (= (kt:cell-value ki:ws 6 18) 100.0) "excel-R-single-block-AIRFLOW")
(vlax-invoke-method kt:book 'Save)
(ki:assert (= (kt:unwrap (vlax-get-property kt:book 'Saved)) :vlax-true) "save-completed")
(kt:cleanup)
(princ (strcat "\nROOM_INPUT_PASS=" (itoa ki:count))) (princ)
