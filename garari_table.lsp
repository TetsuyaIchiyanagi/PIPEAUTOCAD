;; GARARITABLE / Windows AutoCAD 2021+ / Excel / UTF-8, LISPSYS=1 or 2
(vl-load-com)
(setq garari:directory
  (cond
    ((and (boundp '*load-truename*) *load-truename*) (vl-filename-directory *load-truename*))
    ((and (boundp '*load-pathname*) *load-pathname*) (vl-filename-directory *load-pathname*))
    ((findfile "garari_table.lsp") (vl-filename-directory (findfile "garari_table.lsp")))
    ((and (boundp 'pa-path) pa-path (findfile (strcat pa-path "garari_table.lsp"))) pa-path)))
(setq garari:config '((fd-temp . "72") (mesh-spec . "10") (sound . "なし")
  (order . natural) (widths 8 28 28 48) (floor-width . 7) (note-width . 24)
  (page-height . 680) (show-result . T)))
(setq garari:tags '("GARARI" "DIA" "FD" "SHAPE" "MATERIAL" "MESH" "ROOM" "FLOOR" "SOUND"))
(setq garari:keys '("SHAPE" "DIA" "FD" "MATERIAL" "MESH" "MESH_SPEC" "FD_TEMP" "SOUND"))
(defun garari:get (a k) (if (assoc k a) (cdr (assoc k a)) ""))
(defun garari:set (a k v) (if (assoc k a) (subst (cons k v) (assoc k a) a) (cons (cons k v) a)))
(defun garari:trim (s) (vl-string-trim " \t\r\n　" (if s s "")))
(defun garari:half (s) (vl-string-translate
  "０１２３４５６７８９ＡＢＣＤＥＦＧＨＩＪＫＬＭＮＯＰＱＲＳＴＵＶＷＸＹＺａｂｃｄｅｆｇｈｉｊｋｌｍｎｏｐｑｒｓｔｕｖｗｘｙｚ"
  "0123456789ABCDEFGHIJKLMNOPQRSTUVWXYZabcdefghijklmnopqrstuvwxyz" (garari:trim s)))
(defun garari:digits (s / ok c) (setq ok (/= s ""))
  (foreach c (vl-string->list s) (if (or (< c 48) (> c 57)) (setq ok nil))) ok)
(defun garari:dia (s / x)
  (setq x (strcase (garari:half s)))
  (if (member (substr x 1 1) '("φ" "Φ")) (setq x (substr x 2)))
  (cond ((and (>= (strlen x) 2) (= (substr x (1- (strlen x))) "MM")) (setq x (substr x 1 (- (strlen x) 2))))
        ((and (> (strlen x) 0) (member (substr x (strlen x)) '("φ" "Φ"))) (setq x (substr x 1 (1- (strlen x))))))
  (if (and (garari:digits x) (> (atoi x) 0) (< (strlen x) 9)) (itoa (atoi x)) ""))
(defun garari:bool (s / x) (setq x (strcase (garari:half s)))
  (cond ((member x '("あり" "有" "有り" "YES" "Y" "1")) "あり")
        ((member x '("なし" "無" "無し" "NO" "N" "0")) "なし") (T "")))
(defun garari:normalize (raw cfg / out tag s)
  (foreach tag garari:tags
    (setq s (garari:trim (garari:get raw tag)))
    (setq s (cond ((= tag "DIA") (garari:dia s))
      ((member tag '("FD" "MESH")) (garari:bool s))
      ((= tag "SOUND") (if (assoc tag raw) (garari:bool s) (cdr (assoc 'sound cfg))))
      ((= tag "SHAPE") (cond ((member s '("深形" "深型")) "深型") ((member s '("平形" "平型")) "平型") (T "")))
      ((= tag "MATERIAL") (if (member (strcase s) '("SUS" "SUS304" "ステンレス")) "SUS" (strcase s)))
      ((= tag "ROOM") (cond ((/= (garari:bool s) "") (garari:bool s)) (T (strcase (garari:half s)))))
      (T s)))
    (setq out (append out (list (cons tag s)))))
  (append out (list (cons "FD_TEMP" (if (= (garari:get out "FD") "あり") (cdr (assoc 'fd-temp cfg)) ""))
    (cons "MESH_SPEC" (if (= (garari:get out "MESH") "あり") (cdr (assoc 'mesh-spec cfg)) "")))))
(defun garari:issue (severity field message)
  (setq garari:issues (append garari:issues (list (list severity field message)))))
(defun garari:validate (raw norm / tag)
  (foreach tag '("GARARI" "DIA" "FD" "SHAPE" "MATERIAL" "MESH" "ROOM")
    (if (not (assoc tag raw)) (garari:issue "エラー" tag "必要タグ欠落")
      (if (= (garari:trim (garari:get raw tag)) "") (garari:issue "エラー" tag "未入力"))))
  (foreach tag '("DIA" "FD" "SHAPE" "MESH" "SOUND")
    (if (= (garari:get norm tag) "") (garari:issue "エラー" tag "不正値・非対応仕様")))
  (if (= (garari:get norm "ROOM") "あり") (garari:issue "エラー" "ROOM" "室内給気口：品番未入力"))
  (if (vl-string-search "\n" (garari:get norm "GARARI")) (garari:issue "エラー" "GARARI" "記号に改行")))
(defun garari:join (xs sep / s x) (setq s "")
  (foreach x xs (setq s (if (= s "") x (strcat s sep x)))) s)
(defun garari:fail (s) (setq garari:reason s) (exit))

;; Strict single-line RFC4180 fields. Embedded newlines are deliberately rejected.
(defun garari:csv-line (s / i c state field fields)
  (setq i 1 state 'start field "")
  (while (<= i (strlen s))
    (setq c (substr s i 1))
    (cond
      ((eq state 'quoted)
        (if (= c "\"")
          (if (= (substr s (1+ i) 1) "\"") (setq field (strcat field "\"") i (1+ i)) (setq state 'closed))
          (setq field (strcat field c))))
      ((= c ",") (setq fields (cons field fields) field "" state 'start))
      ((eq state 'closed) (garari:fail "CSV：閉じ引用符の後に不正文字"))
      ((= c "\"") (if (eq state 'start) (setq state 'quoted) (garari:fail "CSV：引用符の位置が不正")))
      (T (setq field (strcat field c) state 'plain)))
    (setq i (1+ i)))
  (if (eq state 'quoted) (garari:fail "CSV：引用符未完了／セル内改行は禁止"))
  (reverse (cons field fields)))
(defun garari:master-key (row) (mapcar '(lambda (k) (garari:get row k)) garari:keys))
(defun garari:read-master (path kind / f line headers fields rows row required k seen key n)
  (setq f (open path "r" "utf8-bom"))
  (if (not f) (garari:fail (strcat "マスター読込失敗：" path)))
  (setq garari:file f line (read-line f))
  (if (not line) (garari:fail "空のマスター"))
  (if (and (> (strlen line) 0) (= (ascii (substr line 1 1)) 65279)) (setq line (substr line 2)))
  (setq headers (mapcar 'strcase (garari:csv-line line))
    required (if (= kind "outdoor")
      (append garari:keys '("MANUFACTURER" "MODEL" "SPEC_NOTE" "APPROVED" "SOURCE_URL" "CHECKED_DATE"))
      '("MODEL" "MANUFACTURER" "DIA" "SPEC_NOTE" "APPROVED" "SOURCE_URL" "CHECKED_DATE")))
  (foreach k required (if (not (member k headers)) (garari:fail (strcat "マスター必須列欠落：" k))))
  (foreach k headers (if (member k seen) (garari:fail (strcat "CSV列重複：" k))) (setq seen (cons k seen)))
  (setq seen nil n 1)
  (while (setq line (read-line f))
    (setq n (1+ n))
    (if (/= line "")
      (progn
        (setq fields (garari:csv-line line))
        (if (/= (length fields) (length headers)) (garari:fail (strcat "CSV列数不一致：" (itoa n))))
        (setq row (mapcar 'cons headers (mapcar 'garari:trim fields)))
        (if (not (member (garari:get row "APPROVED") '("0" "1"))) (garari:fail "APPROVEDは0または1"))
        (if (or (= (garari:get row "MODEL") "") (= (garari:dia (garari:get row "DIA")) "")) (garari:fail "マスター品番／径が不正"))
        (if (= kind "outdoor")
          (progn
            (foreach k '("FD" "MESH" "SOUND") (if (not (member (garari:get row k) '("あり" "なし"))) (garari:fail (strcat "マスター正規値不正：" k))))
            (if (not (member (garari:get row "SHAPE") '("深型" "平型"))) (garari:fail "マスターSHAPE不正"))
            (if (or (= (garari:get row "MATERIAL") "")
              (and (= (garari:get row "FD") "なし") (/= (garari:get row "FD_TEMP") ""))
              (and (= (garari:get row "FD") "あり") (not (garari:digits (garari:get row "FD_TEMP"))))
              (and (= (garari:get row "MESH") "なし") (/= (garari:get row "MESH_SPEC") ""))
              (and (= (garari:get row "MESH") "あり") (not (garari:digits (garari:get row "MESH_SPEC"))))) (garari:fail "マスター材質／温度／網目不正"))
            (setq key (garari:master-key row)))
          (setq key (garari:get row "MODEL")))
        (if (member key seen) (garari:issue "エラー" "MASTER" (strcat "マスターキー重複：" path " 行" (itoa n))))
        (setq seen (cons key seen) rows (cons row rows)))))
  (close f) (setq garari:file nil) (reverse rows))

;; CAD extraction: editable and constant attributes, including invisible values.
(defun garari:unwrap (x) (while (= (type x) 'VARIANT) (setq x (vlax-variant-value x))) x)
(defun garari:array (x / r) (setq x (garari:unwrap x))
  (if (= (type x) 'SAFEARRAY)
    (progn (setq r (vl-catch-all-apply 'vlax-safearray->list (list x))) (if (not (vl-catch-all-error-p r)) r))
    (if (listp x) x)))
(defun garari:read-attrs (obj / method result attr tag out)
  (foreach method '(GetAttributes GetConstantAttributes)
    (setq result (vl-catch-all-apply 'vlax-invoke-method (list obj method)))
    (if (vl-catch-all-error-p result) (garari:issue "エラー" "ATTRIBUTES" (vl-catch-all-error-message result))
      (foreach attr (garari:array result)
        (setq tag (strcase (vla-get-TagString attr)))
        (if (assoc tag out) (garari:issue "エラー" tag "属性タグ重複"))
        (setq out (append out (list (cons tag (vla-get-TextString attr)))))
        (vlax-release-object attr)))) out)
(defun garari:name (o / r) (setq r (vl-catch-all-apply 'vlax-get-property (list o 'EffectiveName)))
  (if (vl-catch-all-error-p r) (vla-get-Name o) r))
(defun garari:target (e / d o yes)
  (setq d (entget e))
  (if (and (= (cdr (assoc 0 d)) "INSERT") (= (cdr (assoc 410 d)) "Model")
    (<= (if (assoc 70 d) (cdr (assoc 70 d)) 1) 1)
    (<= (if (assoc 71 d) (cdr (assoc 71 d)) 1) 1))
    (progn (setq o (vlax-ename->vla-object e))
      (setq yes (and (= (strcase (garari:name o)) "GARARI")
        (not (= (vla-get-ObjectName o) "AcDbMInsertBlock"))))
      (vlax-release-object o))) yes)
(defun garari:select-model (norm master / found row)
  (foreach row master (if (and (= (garari:get row "APPROVED") "1") (equal (garari:master-key norm) (garari:master-key row)))
    (setq found (cons row found))))
  (cond ((= (length found) 1) (car found))
    ((null found) (garari:issue "警告" "MODEL" (strcat "選定未登録：" (garari:join (garari:master-key norm) "/"))) nil)
    (T (garari:issue "エラー" "MODEL" "承認済みマスター競合") nil)))
(defun garari:record (raw trace master rooms cfg / garari:issues norm outdoor indoor found room row)
  (setq garari:issues (garari:get trace "ISSUES") norm (garari:normalize raw cfg))
  (garari:validate raw norm)
  (if (/= (garari:get norm "FLOOR") "")
    (progn
      (if (/= (garari:get trace "SELECT_FLOOR") (garari:get norm "FLOOR")) (garari:issue "警告" "FLOOR" "選択階とFLOOR属性が異なる（属性を優先）"))
      (setq trace (garari:set trace "FLOOR" (garari:get norm "FLOOR")))))
  (if (= (garari:get trace "FLOOR") "") (progn (setq trace (garari:set trace "FLOOR" "階未設定")) (garari:issue "警告" "FLOOR" "階未設定")))
  (setq outdoor (garari:select-model norm master) room (garari:get norm "ROOM"))
  (if (not (member room '("" "なし" "あり")))
    (progn
      (foreach row rooms (if (= (garari:get row "MODEL") room) (setq found (cons row found))))
      (cond
        ((> (length found) 1) (garari:issue "エラー" "ROOM" "室内マスター競合"))
        ((or (null found) (/= (garari:get (car found) "APPROVED") "1")) (garari:issue "警告" "ROOM" "室内給気口仕様・適用径要確認"))
        ((/= (garari:get (car found) "DIA") (garari:get norm "DIA")) (garari:issue "エラー" "ROOM" "室内給気口の適用径不一致"))
        (T (setq indoor (car found))))
      (garari:issue "警告" "ROOM" "セットの組合せ・施工適合要確認")))
  (append (list (cons "RAW" raw) (cons "NORM" norm) (cons "OUTDOOR" outdoor) (cons "INDOOR" indoor)
    (cons "ISSUES" garari:issues)) (vl-remove-if '(lambda (x) (= (car x) "ISSUES")) trace)))
(defun garari:add-record-issue (r level field message)
  (garari:set r "ISSUES" (append (garari:get r "ISSUES") (list (list level field message)))))
(defun garari:extract (e floor master rooms cfg / o raw trace garari:issues point r)
  (setq o (vlax-ename->vla-object e) raw (garari:read-attrs o) point (garari:array (vla-get-InsertionPoint o)))
  (setq trace (list (cons "DWG" (strcat (getvar "DWGPREFIX") (getvar "DWGNAME")))
    (cons "HANDLE" (vla-get-Handle o)) (cons "NAME" (garari:name o)) (cons "LAYER" (vla-get-Layer o))
    (cons "POINT" point) (cons "SELECT_FLOOR" floor) (cons "FLOOR" floor) (cons "ISSUES" garari:issues)))
  (vlax-release-object o) (garari:record raw trace master rooms cfg))
(defun garari:signature (r / n) (setq n (garari:get r "NORM"))
  (mapcar '(lambda (k) (garari:get n k)) (append '("DIA" "FD" "SHAPE" "MATERIAL" "MESH" "ROOM") '("MESH_SPEC" "FD_TEMP" "SOUND"))))
(defun garari:symbol (r / s) (setq s (garari:get (garari:get r "NORM") "GARARI"))
  (if (or (= s "") (vl-string-search "\n" s)) (strcat "未設定@" (garari:get r "HANDLE")) s))
(defun garari:cross-check (records / out r other conflict duplicate)
  (foreach r records
    (setq conflict nil duplicate nil)
    (foreach other records
      (if (/= (garari:get r "HANDLE") (garari:get other "HANDLE"))
        (progn
          (if (and (= (garari:symbol r) (garari:symbol other)) (not (equal (garari:signature r) (garari:signature other)))) (setq conflict T))
          (if (equal (garari:get r "POINT") (garari:get other "POINT") 1e-8) (setq duplicate T)))))
    (if conflict (setq r (garari:add-record-issue r "警告" "GARARI" "同一記号の仕様不一致")))
    (if duplicate (setq r (garari:add-record-issue r "警告" "POINT" "同一座標の重複候補（数量を保持）")))
    (setq out (append out (list r)))) out)
(defun garari:less (a b / x y dx dy)
  (setq x (car a) y (car b) dx (garari:digits x) dy (garari:digits y))
  (cond ((and dx dy) (if (= (atof x) (atof y)) (< x y) (< (atof x) (atof y))))
    (dx T) (dy nil)
    ((and (wcmatch x "[a-zA-Z]*") (not (wcmatch y "[a-zA-Z]*"))) T)
    ((and (wcmatch y "[a-zA-Z]*") (not (wcmatch x "[a-zA-Z]*"))) nil)
    (T (< x y))))
(defun garari:stable-sort (items predicate / indexed i item)
  (setq i 0)
  (foreach item items (setq indexed (append indexed (list (cons i item))) i (1+ i)))
  (mapcar 'cdr (vl-sort indexed '(lambda (a b)
    (cond ((apply predicate (list (cdr a) (cdr b))) T)
      ((apply predicate (list (cdr b) (cdr a))) nil) (T (< (car a) (car b))))))))
(defun garari:aggregate (records / groups key pair r)
  (foreach r records
    (setq key (cons (garari:symbol r) (garari:signature r)) pair (assoc key groups))
    (if pair (setq groups (subst (cons key (append (cdr pair) (list r))) pair groups))
      (setq groups (append groups (list (cons key (list r)))))))
  (if (eq (cdr (assoc 'order garari:config)) 'input) groups
    ;; sort indices preserves rows with identical symbols and different specifications
    (garari:stable-sort groups '(lambda (a b) (garari:less (car a) (car b))))))
(defun garari:floor-rank (s / x) (setq x (strcase s))
  (cond ((and (> (strlen x) 2) (= (substr x 1 1) "B") (= (substr x (strlen x)) "F") (garari:digits (substr x 2 (- (strlen x) 2)))) (- (atoi (substr x 2))))
    ((and (> (strlen x) 1) (= (substr x (strlen x)) "F") (garari:digits (substr x 1 (1- (strlen x))))) (atoi x))
    ((= x "RF") 10000) ((= x "階未設定") 10002) (T 10001)))
(defun garari:floors (records / out r)
  (foreach r records (if (not (member (garari:get r "FLOOR") out)) (setq out (append out (list (garari:get r "FLOOR"))))))
  (garari:stable-sort out '(lambda (a b) (< (garari:floor-rank a) (garari:floor-rank b)))))
(defun garari:state (r / s issue) (setq s "正常")
  (foreach issue (garari:get r "ISSUES")
    (cond ((= (car issue) "エラー") (setq s "エラー")) ((and (= s "正常") (= (car issue) "警告")) (setq s "要確認")))) s)
(defun garari:notes (records / xs r issue x)
  (foreach r records (foreach issue (garari:get r "ISSUES") (setq x (caddr issue)) (if (not (member x xs)) (setq xs (append xs (list x))))))
  (garari:join xs "／"))
(defun garari:spec (r / n indoor s)
  (setq n (garari:get r "NORM") indoor (garari:get r "INDOOR"))
  (setq s (strcat (if (= (garari:get n "DIA") "") "径要確認" (strcat (garari:get n "DIA") "φ")) "、"
    (cond ((= (garari:get n "FD") "あり") (strcat "FD付き（" (garari:get n "FD_TEMP") "℃）")) ((= (garari:get n "FD") "なし") "FDなし") (T "FD要確認"))
    "、" (garari:get n "MATERIAL") "、"
    (cond ((= (garari:get n "MESH") "あり") (strcat "防虫網付き（" (garari:get n "MESH_SPEC") "メッシュ）")) ((= (garari:get n "MESH") "なし") "防虫網なし") (T "網要確認"))
    (if (= (garari:get n "SOUND") "あり") "、防音型" "")))
  (if indoor (setq s (strcat s "\n室内：" (garari:get indoor "SPEC_NOTE"))))
  (if (garari:get r "OUTDOOR") (setq s (strcat s "\n" (garari:get (garari:get r "OUTDOOR") "SPEC_NOTE")))) s)

;; Excel objects belong solely to a new application; release every child reference.
(defun garari:own (x) (setq x (garari:unwrap x))
  (setq garari:objects (cons x garari:objects)) x)
(defun garari:drop (x) (vlax-release-object x) (setq garari:objects (vl-remove x garari:objects)))
(defun garari:close-book (book) (vlax-invoke-method book 'Close :vlax-false "" :vlax-false))
(defun garari:open-book (books path)
  (vlax-invoke-method books 'Open path 0 :vlax-false 5 "" "" :vlax-true 2 "" :vlax-false :vlax-false 0 :vlax-false :vlax-true 0))
(defun garari:cleanup (/ x)
  (if garari:file (progn (close garari:file) (setq garari:file nil)))
  (if garari:excel
    (progn
      (vl-catch-all-apply 'vlax-put-property (list garari:excel 'DisplayAlerts :vlax-true))
      (vl-catch-all-apply 'vlax-put-property (list garari:excel 'ScreenUpdating :vlax-true))
      (if (not garari:handed)
        (progn
          (if garari:book (vl-catch-all-apply 'garari:close-book (list garari:book)))
          (vl-catch-all-apply 'vlax-invoke-method (list garari:excel 'Quit))))))
  (foreach x garari:objects (vl-catch-all-apply 'vlax-release-object (list x)))
  (setq garari:objects nil garari:book nil garari:excel nil)
  (if (and garari:temp (findfile garari:temp)) (vl-file-delete garari:temp)) (gc))
(defun garari:col (n / s) (setq s "")
  (while (> n 0) (setq n (1- n) s (strcat (chr (+ 65 (rem n 26))) s) n (fix (/ n 26)))) s)
(defun garari:range (sheet r1 c1 r2 c2)
  (garari:own (vlax-get-property sheet 'Range (strcat (garari:col c1) (itoa r1)) (strcat (garari:col c2) (itoa r2)))))
(defun garari:put-matrix (sheet row data / area arr nr nc)
  (if data
    (progn
      (setq nr (length data) nc (length (car data)) area (garari:range sheet row 1 (+ row nr -1) nc))
      (vlax-put-property area 'NumberFormat "@")
      (setq arr (vlax-make-safearray vlax-vbVariant (cons 1 nr) (cons 1 nc)))
      ;; Excel literal prefix also prevents external strings becoming formulas.
      (vlax-safearray-fill arr (mapcar '(lambda (xs) (mapcar '(lambda (v) (if (= (type v) 'STR) (strcat "'" v) v)) xs)) data))
      (vlax-put-property area 'Value2 (vlax-make-variant arr)) (garari:drop area))))
(defun garari:format (sheet lastrow lastcol / area font borders columns i width)
  (setq area (garari:range sheet 1 1 lastrow lastcol))
  (vlax-put-property area 'WrapText :vlax-true) (vlax-put-property area 'VerticalAlignment -4108)
  (vlax-put-property area 'HorizontalAlignment -4131)
  (setq font (garari:own (vlax-get-property area 'Font))) (vlax-put-property font 'Size 10) (garari:drop font)
  (setq borders (garari:own (vlax-get-property area 'Borders))) (vlax-put-property borders 'LineStyle 1) (vlax-put-property borders 'Weight 2) (garari:drop borders)
  (garari:drop area)
  (setq area (garari:range sheet 1 1 1 lastcol) font (garari:own (vlax-get-property area 'Font)))
  (vlax-put-property font 'Bold :vlax-true) (vlax-put-property area 'RowHeight 30)
  (garari:drop font) (garari:drop area))
(defun garari:sheet (sheets name / s) (setq s (garari:own (vlax-invoke-method sheets 'Add))) (vla-put-Name s name) s)
(defun garari:raw-data (records / header data r n raw tag pt)
  (setq header '("DWG" "HANDLE" "EffectiveName" "LAYER" "X" "Y" "Z" "選択階" "階" "状態" "屋外品番" "室内品番" "エラー" "全原属性（重複含む）"))
  (foreach tag garari:tags (setq header (append header (list (strcat "RAW_" tag) (strcat "NORM_" tag)))))
  (setq header (append header '("MESH_SPEC" "FD_TEMP")) data (list header))
  (foreach r records
    (setq n (garari:get r "NORM") raw (garari:get r "RAW") pt (garari:get r "POINT"))
    (setq data (append data (list (append
      (list (garari:get r "DWG") (garari:get r "HANDLE") (garari:get r "NAME") (garari:get r "LAYER")) pt
      (list (garari:get r "SELECT_FLOOR") (garari:get r "FLOOR") (garari:state r)
        (if (garari:get r "OUTDOOR") (garari:get (garari:get r "OUTDOOR") "MODEL") "要選定")
        (garari:get n "ROOM") (garari:notes (list r)) (vl-prin1-to-string raw))
      (apply 'append (mapcar '(lambda (k) (list (garari:get raw k) (garari:get n k))) garari:tags))
      (list (garari:get n "MESH_SPEC") (garari:get n "FD_TEMP"))))))) data)
(defun garari:error-data (records global / data r issue)
  (setq data (list '("区分" "GARARI" "ハンドル" "レイヤ" "X" "Y" "Z" "項目" "原因")))
  (foreach issue global (setq data (append data (list (append (list (car issue) "" "" "") '("" "" "") (cdr issue))))))
  (foreach r records
    (if (null (garari:get r "ISSUES"))
      (setq data (append data (list (append (list "正常" (garari:symbol r) (garari:get r "HANDLE") (garari:get r "LAYER")) (garari:get r "POINT") '("" "")))))
      (foreach issue (garari:get r "ISSUES")
        (setq data (append data (list (append (list (car issue) (garari:symbol r) (garari:get r "HANDLE") (garari:get r "LAYER")) (garari:get r "POINT") (cdr issue)))))))) data)
(defun garari:table-plan (groups floors / rows blocks g r n outdoor indoor room maker start end vals f count notes)
  (setq rows (list (append '("記号" "名称" "参考型番" "機器仕様") floors '("数量" "備考"))))
  (foreach g groups
    (setq r (cadr g) n (garari:get r "NORM") outdoor (garari:get r "OUTDOOR") indoor (garari:get r "INDOOR") room (garari:get n "ROOM"))
    (setq maker (if outdoor (garari:get outdoor "MANUFACTURER") "屋外メーカー要確認"))
    (if (not (member room '("なし" ""))) (setq maker (strcat "屋外：" maker "／室内：" (if indoor (garari:get indoor "MANUFACTURER") "要確認"))))
    (setq vals nil)
    (foreach f floors (setq count 0) (foreach r (cdr g) (if (= (garari:get r "FLOOR") f) (setq count (1+ count)))) (setq vals (append vals (list count))))
    (setq r (cadr g) start (1+ (length rows)) notes (garari:notes (cdr g)))
    (setq rows (append rows (list (append
      (list (caar g) (if (= room "なし") "ガラリ" "自然給気口＋ガラリ") maker (garari:spec r)) vals
      (list (length (cdr g)) (strcat (garari:get n "SHAPE") (if (= notes "") "" (strcat "／" notes))))))))
    (setq rows (append rows (list (append (list "" "" (strcat "屋外：" (if outdoor (garari:get outdoor "MODEL") "要選定")) "") (mapcar '(lambda (x) "") floors) '("" "")))))
    (if (/= room "なし")
      (setq rows (append rows (list (append (list "" "" (strcat "室内：" (cond ((member room '("" "あり")) "品番未入力") (T room))) "") (mapcar '(lambda (x) "") floors) '("" ""))))))
    (setq end (length rows) blocks (append blocks (list (list start end))))
    (setq rows (append rows (list (mapcar '(lambda (x) "") (car rows))))))
  (list rows blocks))
(defun garari:text-height (s width / chars lines c)
  (setq chars 0 lines 1)
  (foreach c (vl-string->list s)
    (if (= c 10) (setq lines (1+ lines) chars 0)
      (progn (setq chars (+ chars (if (> c 255) 2 1))) (if (> chars width) (setq lines (1+ lines) chars 0)))))
  (+ 12 (* 14 lines)))
(defun garari:write-xlsx (path records groups floors settings global / books sheets table raw errors setup plan rows blocks lastcol widths width col area block start end ht used row vals i page breakobj breaks)
  (setq path (vl-string-translate "/" "\\" path))
  (setq garari:stage "Excel起動")
  (setq garari:excel (garari:own (vlax-create-object "Excel.Application")))
  (vlax-put-property garari:excel 'DisplayAlerts :vlax-false)
  (vlax-put-property garari:excel 'ScreenUpdating :vlax-false)
  (setq books (garari:own (vlax-get-property garari:excel 'Workbooks)) garari:book (garari:own (vlax-invoke-method books 'Add))
    sheets (garari:own (vlax-get-property garari:book 'Worksheets)))
  (setq table (garari:own (vlax-get-property sheets 'Item 1))) (vla-put-Name table "機器表（ガラリ）")
  ;; Remove only extra blank sheets from our freshly created workbook.
  (while (> (vlax-get-property sheets 'Count) 1)
    (setq area (garari:own (vlax-get-property sheets 'Item 2))) (vlax-invoke-method area 'Delete) (garari:drop area))
  (setq raw (garari:sheet sheets "CAD_DATA") errors (garari:sheet sheets "エラー一覧") setup (garari:sheet sheets "選定設定"))
  (setq garari:stage "表データ")
  (setq plan (garari:table-plan groups floors) rows (car plan) blocks (cadr plan) lastcol (+ 6 (length floors)))
  (garari:put-matrix table 1 rows) (garari:format table (length rows) lastcol)
  (setq garari:stage "列幅")
  (setq widths (append (cdr (assoc 'widths garari:config)) (mapcar '(lambda (x) (cdr (assoc 'floor-width garari:config))) floors)
    (list (cdr (assoc 'floor-width garari:config)) (cdr (assoc 'note-width garari:config)))) col 1)
  (foreach ht widths (setq area (garari:range table 1 col (length rows) col))
    (vlax-put-property area 'ColumnWidth ht)
    (if (or (= col 1) (and (> col 4) (< col lastcol))) (vlax-put-property area 'HorizontalAlignment -4108))
    (if (and (> col 4) (< col lastcol)) (vlax-put-property area 'NumberFormat "0"))
    (garari:drop area) (setq col (1+ col)))
  (setq used 30 breaks (garari:own (vlax-get-property table 'HPageBreaks)))
  (setq garari:stage "結合・行高")
  (foreach block blocks
    (setq start (car block) end (cadr block) vals (nth (1- start) rows) ht 30 i 0)
    (foreach width widths
      (if (= (type (nth i vals)) 'STR) (setq ht (max ht (garari:text-height (nth i vals) width))))
      (setq i (1+ i)))
    (setq row start)
    (while (<= row end) (setq ht (max ht (* (- end start -1) (garari:text-height (nth 2 (nth (1- row) rows)) (nth 2 widths))))) (setq row (1+ row)))
    (if (> ht (- (cdr (assoc 'page-height garari:config)) 30)) (garari:fail "1機器がA3ページ高さを超えます。列幅設定を調整してください。"))
    (if (> (+ used ht 12) (cdr (assoc 'page-height garari:config)))
      (progn (setq area (garari:range table start 1 start 1))
        (setq breakobj (garari:own (vlax-invoke-method breaks 'Add area))) (garari:drop breakobj) (garari:drop area) (setq used 30)))
    (setq area (garari:range table start 1 end lastcol)) (vlax-put-property area 'RowHeight (/ ht (- end start -1))) (garari:drop area)
    (setq col 1)
    (repeat lastcol
      (if (/= col 3) (progn (setq area (garari:range table start col end col)) (vlax-invoke-method area 'Merge) (garari:drop area)))
      (setq col (1+ col)))
    (setq area (garari:range table (1+ end) 1 (1+ end) lastcol)) (vlax-put-property area 'RowHeight 12) (garari:drop area)
    (setq used (+ used ht 12)))
  (setq page (garari:own (vlax-get-property table 'PageSetup)))
  (setq garari:stage "印刷設定")
  (vlax-put-property page 'PaperSize 8) (vlax-put-property page 'Orientation 2)
  (vlax-put-property page 'Zoom :vlax-false) (vlax-put-property page 'FitToPagesWide 1) (vlax-put-property page 'FitToPagesTall :vlax-false)
  (vlax-put-property page 'PrintTitleRows "$1:$1")
  (vlax-put-property page 'PrintArea (strcat "$A$1:$" (garari:col lastcol) "$" (itoa (length rows))))
  (vlax-put-property page 'TopMargin 28) (vlax-put-property page 'BottomMargin 28)
  (garari:drop page)
  (setq garari:stage "追跡シート")
  (garari:put-matrix raw 1 (garari:raw-data records))
  (garari:put-matrix errors 1 (garari:error-data records global))
  (garari:put-matrix setup 1 (cons '("設定項目" "値") settings))
  (foreach area (list raw errors setup)
    (setq page (garari:own (vlax-get-property area 'UsedRange)))
    (vlax-put-property page 'ColumnWidth 22) (vlax-put-property page 'WrapText :vlax-true)
    (setq row (garari:own (vlax-get-property page 'Rows))) (vlax-invoke-method row 'AutoFit) (garari:drop row) (garari:drop page))
  (vlax-invoke-method table 'Activate)
  (setq garari:stage "保存")
  ;; Stage beside destination, then rename without overwrite. SaveAs never targets an existing file.
  (setq garari:temp (vl-filename-mktemp "garari-stage-" (vl-filename-directory path) ".xlsx"))
  (if (findfile garari:temp) (vl-file-delete garari:temp))
  (setq garari:stage "SaveAs")
  (vlax-invoke-method garari:book 'SaveAs garari:temp 51 "" "" :vlax-false :vlax-false 1 2 :vlax-false 0 0 :vlax-true)
  (setq garari:stage "Close")
  (garari:close-book garari:book) (setq garari:book nil)
  (setq garari:stage "Rename")
  (if (or (findfile path) (not (vl-file-rename garari:temp path))) (garari:fail "保存先が存在するか、移動できません（上書きなし）"))
  (setq garari:temp nil garari:saved T)
  (vlax-put-property garari:excel 'DisplayAlerts :vlax-true) (vlax-put-property garari:excel 'ScreenUpdating :vlax-true)
  (if (cdr (assoc 'show-result garari:config))
    (progn (setq garari:book (garari:own (garari:open-book books path)))
      (vlax-put-property garari:excel 'Visible :vlax-true) (setq garari:handed T))) T)

(defun garari:output-path (extension / base path)
  (setq base (strcat (getvar "DWGPREFIX") (vl-filename-base (getvar "DWGNAME")) "_ガラリ機器表." extension))
  (if (findfile base) (setq base (vl-filename-mktemp "ガラリ機器表-" (getvar "DWGPREFIX") (strcat "." extension))))
  (setq path (getfiled "ガラリ機器表：新規保存（既存ファイル不可）" base extension 1))
  (while (and path (findfile path)) (princ "\n既存ファイルです。別名を指定してください。") (setq path (getfiled "別名保存" base extension 1))) path)
(defun garari:csv-quote (s / i out c) (if (/= (type s) 'STR) (setq s (vl-princ-to-string s)))
  (setq i 1 out "\"") (while (<= i (strlen s)) (setq c (substr s i 1) out (strcat out (if (= c "\"") "\"\"" c)) i (1+ i))) (strcat out "\""))
(defun garari:write-csv (path records / f row s)
  (setq garari:temp (vl-filename-mktemp "garari-stage-" (vl-filename-directory path) ".csv") f (open garari:temp "w" "utf8-bom") garari:file f)
  (if (not f) (garari:fail "代替CSVの保存失敗"))
  (foreach row (garari:raw-data records)
    (write-line (garari:join (mapcar '(lambda (v) (if (and (= (type v) 'STR) (member (substr v 1 1) '("=" "+" "-" "@"))) (setq v (strcat "'" v))) (garari:csv-quote v)) row) ",") f))
  (close f) (setq garari:file nil)
  (if (or (findfile path) (not (vl-file-rename garari:temp path))) (garari:fail "CSV別名保存失敗")) (setq garari:temp nil))
(defun garari:master-memory-key (name)
  (strcat "PIPEAUTOCAD_GARARI_MASTER_" (strcase (vl-filename-base name))))
(defun garari:master-default (name / previous base)
  (setq previous (getenv (garari:master-memory-key name))
    base (if garari:directory (strcat garari:directory "/" name) name))
  (cond
    ((and previous (/= previous "") (findfile previous)) (findfile previous))
    ((findfile base))
    (T base)))
(defun garari:master-path (name / base)
  ;; 記憶したファイル→LISP所在のCSV。見つからない場合だけ選択画面。
  (setq base (garari:master-default name))
  (if (findfile base) (findfile base)
    (getfiled (strcat "マスターが見つかりません。指定：" name) base "csv" 0)))
(defun garari:remember-masters (outdoor room)
  ;; 2ファイルの読込が成功してから履歴を更新。CSVの内容は毎回読み直す。
  (setenv (garari:master-memory-key "garari_master.csv") outdoor)
  (setenv (garari:master-memory-key "room_master.csv") room))
(defun c:GARARIMASTERSET (/ *error* garari:reason garari:file garari:issues outdoor room)
  (defun *error* (msg)
    (if garari:file (close garari:file))
    (princ (strcat "\nGARARIMASTERSET：" (if garari:reason garari:reason msg))) (princ))
  (if (= (getvar "LISPSYS") 0) (garari:fail "LISPSYS=1または2で実行してください。"))
  (if (not (setq outdoor (getfiled "屋外ガラリマスターを変更"
    (garari:master-default "garari_master.csv") "csv" 0))) (garari:fail "キャンセル（履歴変更なし）"))
  (garari:read-master outdoor "outdoor")
  (if (not (setq room (getfiled "室内給気口マスターを変更"
    (garari:master-default "room_master.csv") "csv" 0))) (garari:fail "キャンセル（履歴変更なし）"))
  (garari:read-master room "room")
  (garari:remember-masters outdoor room)
  (princ (strcat "\nマスター指定を記憶しました。\n屋外：" outdoor "\n室内：" room
    "\nマスター警告／エラー=" (itoa (length garari:issues)))) (princ))
(defun garari:summary (records groups floors excluded / normal warning errors r f qty)
  (setq normal 0 warning 0 errors 0 qty 0)
  (foreach r records (cond ((= (garari:state r) "正常") (setq normal (1+ normal))) ((= (garari:state r) "エラー") (setq errors (1+ errors))) (T (setq warning (1+ warning)))))
  (foreach r groups (setq qty (+ qty (length (cdr r)))))
  (if (/= qty (length records)) (garari:fail "集計数量と採用数が一致しません"))
  (princ (strcat "\n採用ユニークブロック=" (itoa (length records)) " 正常=" (itoa normal) " 要確認=" (itoa warning) " エラー=" (itoa errors) " 数量合計=" (itoa qty) " 選択対象外=" (itoa excluded)))
  (foreach f floors (setq qty 0) (foreach r records (if (= (garari:get r "FLOOR") f) (setq qty (1+ qty)))) (princ (strcat "\n" f "=" (itoa qty))))
  (princ "\n対象外：ペーパー空間・Xref内・入れ子・MINSERT。モデル空間の凡例は手動で除外。"))
(defun c:GARARITABLE (/ *error* garari:stage garari:objects garari:excel garari:book garari:handed garari:temp garari:saved garari:file garari:reason garari:issues
  cfg master rooms mp rp records seen floor ss i e h pair result r groups floors excluded global path settings value)
  (defun *error* (msg) (garari:cleanup) (princ (strcat "\nGARARITABLE：" (if garari:reason garari:reason msg))) (princ))
  (if (= (getvar "LISPSYS") 0) (garari:fail "UTF-8用にLISPSYS=1または2を利用者が設定し、AutoCADを再起動してください。"))
  (setq cfg garari:config excluded 0)
  (princ (strcat "\nGARARITABLE：階ごとに選択 / FD_TEMP=" (cdr (assoc 'fd-temp cfg)) "℃ / MESH_SPEC=" (cdr (assoc 'mesh-spec cfg)) " / SOUND既定=" (cdr (assoc 'sound cfg))))
  (initget 6) (setq value (getint "\n案件FD温度 <72>：")) (if value (setq cfg (garari:set cfg 'fd-temp (itoa value))))
  (initget 6) (setq value (getint "\n案件防虫網メッシュ数 <10>：")) (if value (setq cfg (garari:set cfg 'mesh-spec (itoa value))))
  (initget "Yes No") (setq value (getkword "\nSOUNDタグ欠落時の防音指定 [Yes/No] <No>：")) (setq cfg (garari:set cfg 'sound (if (= value "Yes") "あり" "なし")))
  (if (not (setq mp (garari:master-path "garari_master.csv"))) (garari:fail "キャンセル"))
  (setq master (garari:read-master mp "outdoor"))
  (if (not (setq rp (garari:master-path "room_master.csv"))) (garari:fail "キャンセル"))
  (setq rooms (garari:read-master rp "room") global garari:issues garari:issues nil)
  (garari:remember-masters mp rp)
  (princ (strcat "\n使用マスター（自動読込）：\n屋外：" mp "\n室内：" rp))
  (while (/= (setq floor (garari:trim (getstring T "\n選択階名（1F / 2F / B1F等、Enterで選択終了）："))) "")
    (princ (strcat "\n" floor " の設備を選択：")) (setq ss (ssget))
    (if ss (progn (setq i 0) (repeat (sslength ss)
      (setq e (ssname ss i) i (1+ i))
      (if (garari:target e)
        (progn (setq h (cdr (assoc 5 (entget e))) pair (assoc h seen))
          (if pair
            (if (/= (cdr pair) floor)
              (progn (setq r (car (vl-remove-if-not '(lambda (x) (= (garari:get x "HANDLE") h)) records)))
                (setq records (subst (garari:add-record-issue r "エラー" "FLOOR" (strcat "階割当競合：" (cdr pair) "／" floor)) r records))))
            (progn (setq r (garari:extract e floor master rooms cfg))
              (setq records (append records (list r)) seen (cons (cons h floor) seen)))))
        (setq excluded (1+ excluded)))))))
  (if (null records) (garari:fail "対象GARARIブロックなし"))
  (setq records (garari:cross-check records) groups (garari:aggregate records) floors (garari:floors records))
  (garari:summary records groups floors excluded)
  (princ (strcat "\nマスター等の全体警告／エラー=" (itoa (length global))))
  (setq settings (list (list "集計日時（AutoCADローカル）" (rtos (getvar "CDATE") 2 6))
    (list "DWG" (strcat (getvar "DWGPREFIX") (getvar "DWGNAME"))) (list "選択方式" "階ごとに範囲選択、FLOOR優先")
    (list "階列" (garari:join floors "/")) (list "屋外マスター" mp) (list "屋外マスター更新日時" (vl-prin1-to-string (vl-file-systime mp)))
    (list "室内マスター" rp) (list "室内マスター更新日時" (vl-prin1-to-string (vl-file-systime rp)))
    (list "FD_TEMP（タグで指定しない）" (cdr (assoc 'fd-temp cfg))) (list "MESH_SPEC（屋外）" (cdr (assoc 'mesh-spec cfg)))
    (list "SOUNDタグ欠落時" (cdr (assoc 'sound cfg))) (list "選択対象外数" excluded)
    (list "対象外条件" "ペーパー空間・Xref内・入れ子・MINSERT。モデル凡例は手動除外")
    (list "選定範囲" "参考型番。風量・圧損・雨仕舞・法規・組合せ施工適合は設計者確認")
    (list "マスター版" "v1 / CHECKED_DATEは各行に記載")))
  (if (not (setq path (garari:output-path "xlsx"))) (garari:fail "キャンセル"))
  (setq result (vl-catch-all-apply 'garari:write-xlsx (list path records groups floors settings global)))
  (if (vl-catch-all-error-p result)
    (progn
      (garari:cleanup)
      (princ (strcat "\nExcel出力失敗：" (if garari:reason garari:reason (vl-catch-all-error-message result))))
      (if garari:saved (princ (strcat "\n保存済み（表示失敗）：" path))
        (progn
          (princ "\n整形xlsx未作成。")
          (if (not (wcmatch (strcase (vl-catch-all-error-message result)) "*CANCEL*,*QUIT*,*ABORT*,*BREAK*"))
            (progn (initget "Yes No")
              (if (= (getkword "\nCAD_DATA相当CSVを代替保存しますか [Yes/No] <No>：") "Yes")
                (if (setq path (garari:output-path "csv")) (progn (garari:write-csv path records) (princ (strcat "\n代替CSV保存（整形xlsx未作成）：" path))))))))))
    (princ (strcat "\nGARARITABLE 作成完了：" path)))
  (garari:cleanup) (princ))
(princ "\nGARARITABLE loaded. Commands: GARARITABLE / GARARIMASTERSET") (princ)
