;; Synthetic block definition and placements in the disposable blank DWG.
(setq kr:count 0)
(defun kr:assert (condition label)
  (if (not condition) (progn (princ (strcat "\nFAIL: " label)) (exit)))
  (setq kr:count (1+ kr:count)) (princ (strcat "\nPASS: " label)))
(if (tblsearch "BLOCK" "KANKI_KIKI")
  (progn (princ "\n試験中止：KANKI_KIKIのない破棄可能な新規空図面だけを使用してください。") (exit)))
(setq kr:doc (vla-get-ActiveDocument (vlax-get-acad-object)) kr:blocks (vla-get-Blocks kr:doc)
  kr:def (vla-Add kr:blocks (vlax-3d-point '(0.0 0.0 0.0)) "KANKI_KIKI"))
(foreach kr:tag '("SYSTEM" "NUM" "MODEL" "LOCATION" "FLOOR" "KIKI_NO" "CUSTOM")
  (setq kr:o (vla-AddAttribute kr:def 2.5 1 kr:tag (vlax-3d-point '(0.0 0.0 0.0)) kr:tag ""))
  (vlax-release-object kr:o))
(setq kr:model (vla-get-ModelSpace kr:doc)
  kr:insert (vla-InsertBlock kr:model (vlax-3d-point '(0.0 0.0 0.0)) "KANKI_KIKI" 1.0 1.0 1.0 0.0)
  kr:handle (vla-get-Handle kr:insert))
(foreach kr:att (kt:attribute-objects kr:insert 'GetAttributes)
  (vla-put-TextString kr:att (strcat "KEEP-" (vla-get-TagString kr:att))))
(setq kr:before (kc:attr-text kr:insert))
(foreach kr:o kt:objects (vlax-release-object kr:o)) (setq kt:objects nil)
(vlax-release-object kr:insert)
(c:KANKIROOMATTR)
(setq kr:insert (vlax-ename->vla-object (handent kr:handle)) kr:after (kc:attr-text kr:insert))
(foreach kr:pair kr:before
  (kr:assert (equal (cdr kr:pair) (cdr (assoc (car kr:pair) kr:after))) (strcat "migration-preserves-" (car kr:pair))))
(kr:assert (assoc "FLOOR_AREA" kr:after) "migration-adds-floor-area")
(kr:assert (assoc "CEILING_HEIGHT" kr:after) "migration-adds-ceiling-height")
(setq kr:attrs (kt:attribute-objects kr:insert 'GetAttributes))
(foreach kr:att kr:attrs
  (cond ((= (vla-get-TagString kr:att) "FLOOR_AREA") (vla-put-TextString kr:att "43.7"))
        ((= (vla-get-TagString kr:att) "CEILING_HEIGHT") (vla-put-TextString kr:att "2.4"))))
(ks:update kr:attrs '(("MODEL" . "NEW-MODEL") ("LOCATION" . "WRONG") ("FLOOR" . "9")
  ("FLOOR_AREA" . "999") ("CEILING_HEIGHT" . "9")))
(setq kr:after (kc:attr-text kr:insert))
(kr:assert (= (cdr (assoc "MODEL" kr:after)) "NEW-MODEL") "kikiset-updates-model")
(kr:assert (= (cdr (assoc "LOCATION" kr:after)) "KEEP-LOCATION") "kikiset-keeps-location")
(kr:assert (= (cdr (assoc "FLOOR" kr:after)) "KEEP-FLOOR") "kikiset-keeps-floor")
(kr:assert (= (cdr (assoc "FLOOR_AREA" kr:after)) "43.7") "kikiset-keeps-actual-area")
(kr:assert (= (cdr (assoc "CEILING_HEIGHT" kr:after)) "2.4") "kikiset-keeps-actual-height")
(foreach kr:o kt:objects (vlax-release-object kr:o)) (setq kt:objects nil)
(vlax-release-object kr:insert)
(c:KANKIROOMATTR)
(setq kr:insert (vlax-ename->vla-object (handent kr:handle)) kr:after (kc:attr-text kr:insert))
(kr:assert (= (cdr (assoc "FLOOR_AREA" kr:after)) "43.7") "migration-repeat-keeps-area")
(kr:assert (= (cdr (assoc "CEILING_HEIGHT" kr:after)) "2.4") "migration-repeat-keeps-height")
(foreach kr:o kt:objects (vlax-release-object kr:o)) (setq kt:objects nil)
(foreach kr:o (list kr:insert kr:model kr:def kr:blocks kr:doc) (vlax-release-object kr:o))
(princ (strcat "\nKANKI_ATTRIBUTE_PASS_TOTAL=" (itoa kr:count))) (princ)
