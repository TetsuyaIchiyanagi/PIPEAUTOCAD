;; Full native Excel transaction against a disposable copy of the user's ver03.
(setq kv:count 0)
(defun *error* (msg) (princ (strcat "\nREGRESSION_ERROR: " msg " / " (if kt:reason kt:reason ""))) (kt:cleanup) (princ))
(defun kv:assert (ok label)
  (if (not ok) (progn (princ (strcat "\nFAIL: " label)) (exit)))
  (setq kv:count (1+ kv:count)) (princ (strcat "\nPASS: " label)))
(defun kv:records (raw / matrix headers row data i result value)
  (setq matrix (kc:read raw 1 1 (kt:last raw 'Row) (kt:last raw 'Column)) headers (car matrix))
  (foreach row (cdr matrix)
    (if (car row)
      (progn (setq data nil i 0)
        (foreach value row
          (setq data (cons (cons (nth i headers) (kc:text value)) data) i (1+ i)))
        (setq result (append result (list (cons (cons "HANDLE" (strcat "V" (itoa (length result)))) (kt:derive data)))))))) result)
(defun kv:row (ws room / rows r found entry)
  (setq rows (kc:read ws 6 4 kc:verify-end 4) r 6)
  (foreach entry rows (if (= (car entry) room) (setq found r)) (setq r (1+ r))) found)
(defun kv:formulas (ws r1 c1 r2 c2 / area result)
  (setq area (kt:range ws r1 c1 r2 c2) result (kt:array (vlax-get-property area 'Formula)))
  (kt:drop area) result)
(setq kt:config (append kt:vent-config kt:aircon-config) kt:tags kt:vent-tags kt:raw-tags (kt:raw-columns))
(kt:open kr:fixture)
(setq kv:sheets (kt:own (vlax-get-property kt:book 'Worksheets))
  kv:ws (kt:sheet kv:sheets kc:sheet-name) kv:raw (kt:sheet kv:sheets "CAD_DATA_KANKI")
  kv:records (kv:records kv:raw) kv:header (kc:read kv:ws 3 3 5 22)
  kv:left (kv:formulas kv:ws 6 1 24 2) kv:width (kt:range kv:ws 1 22 1 22))
(setq kv:width-value (kt:unwrap (vlax-get-property kv:width 'ColumnWidth))) (kt:drop kv:width)
(kv:assert (= (length kv:records) 10) "actual-ver03-ten-raw-block-records")
(kv:assert (not (vl-catch-all-error-p (vl-catch-all-apply 'kc:headers (list kv:ws)))) "actual-ver03-headers-accepted")
(kv:assert (kc:remarks-p kv:ws) "V-is-manual-remarks")
(kt:write-book kv:records (kt:group kv:records))
(setq kv:ws kc:verify-sheet kv:locker (kv:row kv:ws "ロッカールーム") kv:sterile (kv:row kv:ws "消毒室"))
(setq kv:width (kt:range kv:ws 1 22 1 22))
(princ (strcat "\nVER03_WIDTH initial=" (vl-princ-to-string kv:width-value) " after-first=" (vl-princ-to-string (vlax-get-property kv:width 'ColumnWidth)))) (kt:drop kv:width)
(kv:assert (= (length (kc:rooms kv:records)) 9) "nine-rooms-one-missing-floor-excluded")
(kv:assert (= (kt:cell-value kv:ws 3 18) "必要換気能力") "R3-heading-not-renamed")
(kv:assert (= (kt:cell-value kv:ws 3 22) "備考") "V3-heading-not-renamed")
(kv:assert (equal kv:header (kc:read kv:ws 3 3 5 22)) "all-original-headers-preserved")
(kv:assert (= (kt:cell-value kv:ws kv:locker 22) "強設定") "original-room-remarks-preserved")
(kv:assert (= (kt:cell-value kv:ws kv:locker 8) 4.0) "original-person-count-preserved")
(kv:assert (= (kt:cell-value kv:ws kv:sterile 8) 2.0) "other-room-person-count-preserved")
(kv:assert (= (kt:cell-value kv:ws kv:locker 17) 3.0) "original-ventilation-method-preserved")
(kv:assert (= (kt:cell-value (kt:sheet kv:sheets "CAD_DATA") 1 1) "SYSTEM") "aircon-raw-not-replaced")
(kv:assert (equal kv:left (kv:formulas kv:ws 6 1 24 2)) "A-B-original-values-and-formulas-preserved")
(kv:assert (= (kt:cell-value kv:ws 16 3) "1F") "outside-print-area-floor-placeholder-preserved")
;; A later CAD update must keep edited V-column notes with the same room.
(kt:put kv:ws kv:locker 22 "手入力備考を保持")
(setq kv:many kv:records kv:i 1)
(repeat 23
  (setq kv:many (append kv:many (list (list '("SYSTEM" . "TEST_EF") '("NUM" . "1") '("MODEL" . "TEST430")
    '("TYPE" . "機器形式テスト") '("EQUIP_TYPE" . "換気扇") '("FLOOR" . "0")
    (cons "LOCATION" (strcat "追加室" (itoa kv:i))) '("FLOOR_AREA" . "43.7") '("CEILING_HEIGHT" . "2.4")
    '("AIRFLOW" . "430") '("STATIC_PRESSURE" . "80") (cons "HANDLE" (strcat "NEW" (itoa kv:i))))))
    kv:i (1+ kv:i)))
(kt:write-book kv:many (kt:group kv:many))
(setq kv:ws kc:verify-sheet kv:locker (kv:row kv:ws "ロッカールーム"))
(kv:assert (= kc:verify-end 37) "ver03-expanded-to-32-valid-rooms")
(kv:assert (= (kt:cell-value kv:ws kv:locker 22) "手入力備考を保持") "remarks-follow-room-after-reorder")
(kv:assert (= (kt:cell-value kv:ws kv:locker 8) 4.0) "persons-follow-room-after-reorder")
(kv:assert (= (kt:cell-value kv:ws 6 4) "追加室1") "new-floor-numeric-order")
(kv:assert (member (kt:cell-value kv:ws 6 22) '(nil "")) "new-room-remarks-blank-not-TYPE")
(kv:assert (equal (kt:cell-value kv:ws 6 7) 104.88 1e-9) "new-room-volume-calculated")
(kv:assert (= (kt:cell-value kv:ws 38 3) "1F") "lower-data-moved-intact")
(kv:assert (= (kc:end kv:ws) 37) "ver03-print-range-expanded")
;; Preserve note/conditions in the existing old-settings archive on removal.
(setq kv:remaining (vl-remove-if '(lambda (r) (= (kt:get r "LOCATION") "ロッカールーム")) kv:records))
(kt:write-book kv:remaining (kt:group kv:remaining))
(setq kv:ws kc:verify-sheet)
(kv:assert (= kc:verify-end 13) "ver03-shrink-to-eight-valid-rooms")
(kv:assert (member (kt:cell-value kv:ws 14 4) '(nil "")) "ver03-no-stale-room-after-shrink")
(kv:assert (member (kt:cell-value kv:ws 14 22) '(nil "")) "ver03-no-stale-remark-after-shrink")
(setq kv:archive (kt:sheet kv:sheets kc:archive-name))
(kv:assert (vl-some '(lambda (r) (member "手入力備考を保持" r))
  (kc:read kv:archive 2 1 (kt:last kv:archive 'Row) 28)) "deleted-room-note-recoverable")
(setq kv:width (kt:range kv:ws 1 22 1 22))
(princ (strcat "\nVER03_WIDTH before-save=" (vl-princ-to-string (vlax-get-property kv:width 'ColumnWidth))))
(kv:assert (= kv:width-value (kt:unwrap (vlax-get-property kv:width 'ColumnWidth))) "V-column-width-preserved") (kt:drop kv:width)
(vlax-invoke-method kt:book 'Save)
(kv:assert (= (kt:unwrap (vlax-get-property kt:book 'Saved)) :vlax-true) "ver03-saved-successfully")
(kt:cleanup)
(kt:open kr:fixture)
(setq kv:sheets (kt:own (vlax-get-property kt:book 'Worksheets)) kv:ws (kt:sheet kv:sheets kc:sheet-name))
(kv:assert (= (kt:cell-value kv:ws 3 18) "必要換気能力") "saved-ver03-reopened")
(kv:assert (= (kt:cell-value kv:ws 3 22) "備考") "saved-remarks-header-retained")
(kv:assert (= (kt:cell-value kv:ws 38 3) "1F") "saved-lower-data-retained")
(kt:cleanup)
(princ (strcat "\nKANKI_VER03_PASS=" (itoa kv:count))) (princ)
