;; KIKITABLE.lspを先にロードし、KIKITABLETESTを実行する。
;; 集計・空配列変換の試験。図面・Excelは変更しない。
(defun ktt:assert (ok label)
  (if ok (setq ktt:passed (1+ ktt:passed))
    (progn (princ (strcat "\nFAIL: " label)) (exit))))
(defun ktt:record (key place floor note / split)
  (setq split (vl-string-search "-" key))
  (list (cons "SYSTEM" (if split (substr key 1 split) ""))
    (cons "NUM" (if split (substr key (+ split 2)) ""))
    (cons "LOCATION" place) (cons "FLOOR" floor)
    (cons "NOTE" note) '("MAKER" . "三菱電機")
    '("MODEL" . "PLZ-ZRMP112HF6") '("SYSTEM_TYPE" . "空冷ヒートポンプ式パッケージエアコン")
    '("TYPE" . "4方向天井カセット形（i-スクエアタイプ）")
    '("COOL_CAP" . "10.0") '("HEAT_CAP" . "11.2") '("COOL_POWER" . "2.17")
    '("HEAT_POWER" . "2.22") '("COMP_POWER" . "2.10") '("FAN_IN" . "0.120")
    '("FAN_OUT" . "0.060×2") '("PHASE" . "3φ") '("VOLT" . "200")
    '("リモコン" . "ワイヤードリモコン") '("FREQ" . "50")
    '("GAS_PIPE" . "15.88") '("LIQ_PIPE" . "9.52")))
(defun ktt:planned (row col / found item)
  (foreach item kt:plan
    (if (and (= row (car item)) (= col (cadr item))) (setq found (caddr item)))) found)
(defun ktt:empty-array (/ dictionary result)
  ;; AutoLISP自身では要素0のSAFEARRAYを生成できないためWindows COMから取得する。
  (setq dictionary (vlax-create-object "Scripting.Dictionary")
        result (vl-catch-all-apply 'vlax-invoke-method (list dictionary 'Items)))
  (vlax-release-object dictionary)
  (if (vl-catch-all-error-p result) (progn (princ (vl-catch-all-error-message result)) (exit)))
  result)
(defun c:KIKITABLETEST (/ ktt:passed kt:warnings kt:plan base second records groups data specs buckets i empty)
  (setq ktt:passed 0)
  (ktt:assert (null (kt:array nil)) "Missing attribute array")
  (setq empty (ktt:empty-array))
  (ktt:assert (null (kt:array (kt:unwrap empty))) "Empty attribute array")
  (ktt:assert (null (kt:array empty)) "Wrapped empty attribute array")
  (ktt:assert (equal (kt:array (vlax-safearray-fill (vlax-make-safearray vlax-vbInteger '(1 . 2)) '(7 8))) '(7 8)) "Nonempty attribute array conversion")
  (ktt:assert (equal (vl-sort '("PAC-10" "PAC-2" "RAC-1" "PAC-1" "PAC-11") 'kt:natural-less)
                      '("PAC-1" "PAC-2" "PAC-10" "PAC-11" "RAC-1")) "Natural order")
  (ktt:assert (kt:natural-less "PAC-99999999999999" "PAC-100000000000000") "Long numeric suffix")
  (ktt:assert (= (kt:floor "02") "2") "Floor normalization")
  (ktt:assert (null (kt:floor "2F")) "Reject floor unit")
  (ktt:assert (null (kt:floor "")) "Reject empty floor")
  (ktt:assert (equal (kt:number "0") 0.0) "Zero is numeric")
  (ktt:assert (null (kt:number "2.2kW")) "Reject partial number")
  (ktt:assert (null (kt:number "2.2.3")) "Reject malformed number")
  (ktt:assert (= (kt:power-text "0.060×2") "0.060kW×2") "Motor multiplication")
  (ktt:assert (= (kt:power-text "") "") "Missing power")
  (setq base (ktt:record "PAC-7" "職員室" "2" "共通備考")
        second (ktt:record "PAC-7" "会議室" "1" "共通備考")
        records (list base second base) groups (kt:group records)
        data (kt:consensus "PAC-7" records) specs (kt:spec data))
  (ktt:assert (= (length groups) 1) "Group by equipment number")
  (ktt:assert (= (length (cdar groups)) 3) "Keep duplicate instances")
  (ktt:assert (= (nth 2 specs) "冷房能力10.0kW　暖房能力11.2kW") "Capacity sentence")
  (ktt:assert (= (nth 4 specs) "圧縮機出力2.10kW　室内送風機出力0.120kW　室外送風機出力0.060kW×2") "Motor sentence")
  (ktt:assert (equal (kt:max-power "PAC-7" data) 2.22 1e-10) "Maximum power")
  (ktt:assert (= (nth 2 (kt:spec '(("COOL_CAP" . "10.0")))) "冷房能力10.0kW") "Omit missing heat phrase")
  (kt:plan-group (car groups) 0 '(("1" . 10) ("2" . 11)) 12 13)
  (ktt:assert (= (ktt:planned 6 2) "PAC-7") "Start B6")
  (ktt:assert (= (ktt:planned 6 3) "空調調和機") "Fixed equipment name without attribute")
  (ktt:assert (= (ktt:planned 6 7) "3") "Phase without phi")
  (ktt:assert (= (ktt:planned 11 5) "ワイヤードリモコン、その他付属品一式") "Remote control sentence")
  (ktt:assert (= (ktt:planned 7 4) "PLZ-ZRMP112HF6") "Model D7")
  (ktt:assert (= (ktt:planned 6 6) "職員室(2)") "Aggregate location")
  (ktt:assert (= (ktt:planned 6 11) 2) "Two units on floor 2")
  (ktt:assert (= (ktt:planned 7 10) 1) "One unit on floor 1")
  (ktt:assert (= (ktt:planned 7 12) 3) "Quantity at last location")
  (ktt:assert (= (ktt:planned 6 13) "共通備考") "Common note once")
  (ktt:assert (null (ktt:planned 7 13)) "No repeated common note")
  (setq kt:plan nil)
  (kt:plan-group (car groups) 1 '(("2" . 10) ("1" . 11)) 12 13)
  (ktt:assert (= (ktt:planned 13 2) "PAC-7") "Seven row pitch")
  (ktt:assert (= (ktt:planned 13 10) 2) "Dynamic reversed floor columns")
  (setq data (kt:consensus "PAC-7" (list base (subst '("MODEL" . "OTHER") (assoc "MODEL" base) base))))
  (ktt:assert (= (kt:get data "MODEL") "") "Conflicting model left blank")
  (ktt:assert (> (length kt:warnings) 0) "Conflict warning")
  (setq kt:plan nil kt:warnings nil records nil i 1)
  (repeat 8
    (setq records (append records (list (ktt:record "PAC-7" (strcat "Room" (itoa i)) "2" ""))) i (1+ i)))
  (kt:plan-group (car (kt:group records)) 0 '(("2" . 10)) 11 12)
  (ktt:assert (= (ktt:planned 11 6) "Room6\nRoom7\nRoom8") "All overflow locations retained")
  (ktt:assert (= (ktt:planned 11 10) "1\n1\n1") "Aligned overflow floor counts")
  (ktt:assert (= (ktt:planned 11 11) 8) "Overflow total")
  (ktt:assert (= (length kt:warnings) 1) "Overflow warning")
  (setq kt:plan nil kt:warnings nil)
  (kt:plan-group (car (kt:group (list base (subst '("NOTE" . "別備考") (assoc "NOTE" base) base))))
    0 '(("2" . 10)) 11 12)
  (ktt:assert (= (ktt:planned 6 12) "共通備考") "Note per location row 1")
  (ktt:assert (= (ktt:planned 7 12) "別備考") "Note per location row 2")
  (ktt:assert (null (kt:group (list (ktt:record "" "Room" "1" ""))))
    "Blank equipment number excluded")
  (ktt:assert (= (kt:key '(("SYSTEM" . "RAC") ("NUM" . "3"))) "RAC-3") "No fixed prefix")
  (ktt:assert (= (kt:key '(("SYSTEM" . "PAC") ("NUM" . "02"))) "PAC-02") "Preserve number spelling")
  (ktt:assert (= (kt:key '(("KIKI_NO" . "OLD") ("SYSTEM" . "PAC") ("NUM" . "2"))) "PAC-2") "Ignore legacy key")
  (ktt:assert (= (kt:get (kt:derive base) "KIKI_NO") "PAC-7") "Derived raw column")
  (ktt:assert (= (kt:get (kt:derive base) "NUM") "7") "Keep raw number")
  (ktt:assert (= (kt:get (kt:derive '(("SYSTEM" . " PAC ") ("NUM" . " 2 "))) "SYSTEM") " PAC ") "Keep raw spaces")
  (ktt:assert (= (nth 5 (kt:spec '(("リモコン" . "ワイヤレスリモコン")))) "ワイヤレスリモコン、その他付属品一式") "Wireless remote")
  (ktt:assert (= (nth 5 (kt:spec nil)) "その他付属品一式") "Missing remote no leading comma")
  (ktt:assert (= (kt:power-text "0.12") "0.12kW") "No precision adjustment")
  (ktt:assert (= (kt:capacity "4") "4.0") "Integer capacity decimal")
  (ktt:assert (= (kt:capacity "2.8") "2.8") "Decimal capacity")
  (ktt:assert (= (kt:capacity "2.86") "2.9") "Capacity rounds to one decimal")
  (ktt:assert (= (kt:capacity "0") "0.0") "Zero capacity")
  (ktt:assert (= (kt:capacity "") "") "Empty capacity")
  (ktt:assert (= (kt:phase-text "１Φ") "１") "Fullwidth number and capital phi")
  (ktt:assert (= (kt:phase-text "1φ") "1") "Lowercase phi")
  (ktt:assert (= (kt:phase-text "3") "3") "Phase without symbol unchanged")
  (setq groups (kt:group (list (ktt:record "RAC-1" "" "1" "") (ktt:record "PAC-10" "" "1" "")
                               (ktt:record "PAC-2" "" "1" "") (ktt:record "PAC-1" "" "1" ""))))
  (ktt:assert (equal (mapcar 'car groups) '("PAC-1" "PAC-2" "PAC-10" "RAC-1")) "System then numeric number")
  (setq kt:warnings nil)
  (kt:validate-record '(("SYSTEM" . "PAC") ("NUM" . "2") ("MODEL" . "M")) "TEST")
  (ktt:assert (null kt:warnings) "Optional missing attributes do not warn")
  (kt:validate-record '(("SYSTEM" . "PAC") ("NUM" . "")) "TEST")
  (ktt:assert (= (length kt:warnings) 2) "Missing number and model warn")
  (princ (strcat "\nKIKITABLETEST PASSED: " (itoa ktt:passed))) (princ))
