;; Run in isolated AutoCAD with disposable fixtures and xt:directory set.
;; The runner keeps busy.xlsx open in another Excel with an unsaved workbook.
(setq xt:count 0)
(defun *error* (message)
  (princ (strcat "\nLIFECYCLE_ERROR: " message)) (kt:cleanup) (ks:close-excel) (princ))
(defun xt:assert (ok label)
  (if (not ok) (progn (princ (strcat "\nFAIL: " label)) (exit)))
  (setq xt:count (1+ xt:count)) (princ (strcat "\nPASS: " label)))
(defun xt:export (category path / kt:objects kt:excel kt:book kt:reason kt:stage kt:log-path kt:config kt:tags kt:raw-tags kt:warnings kt:plan records result sheets)
  (setq kt:config (if (= category "KANKI") (append kt:vent-config kt:aircon-config) kt:aircon-config)
    kt:tags (if (= category "KANKI") kt:vent-tags kt:aircon-tags) kt:raw-tags (kt:raw-columns)
    records '((("SYSTEM" . "EF") ("NUM" . "1") ("MODEL" . "TEST") ("MAKER" . "TEST")
      ("LOCATION" . "試験室") ("FLOOR" . "1") ("FLOOR_AREA" . "10") ("CEILING_HEIGHT" . "3")
      ("EQUIP_TYPE" . "換気扇") ("AIRFLOW" . "100") ("STATIC_PRESSURE" . "30") ("DUCT_DIA" . "100"))))
  (kt:open path)
  (kt:write-book records (kt:group records))
  (setq sheets (kt:own (vlax-get-property kt:book 'Worksheets)))
  (xt:assert (= (kt:cell-value (kt:sheet sheets (kt:cfg 'sheet)) 6 2) "EF-1") (strcat category "-equipment-written"))
  (if (= category "KANKI")
    (xt:assert (= (kt:cell-value (kt:sheet sheets kc:sheet-name) 6 4) "試験室") "room-calculation-template-copied"))
  (vlax-invoke-method kt:book 'Save)
  (xt:assert (= (kt:unwrap (vlax-get-property kt:book 'Saved)) :vlax-true) (strcat category "-saved"))
  (kt:cleanup) (kt:cleanup)
  (xt:assert (and (null kt:objects) (null kt:book) (null kt:excel)) (strcat category "-cleanup-idempotent")))
(defun xt:refused (path expected-stage / kt:objects kt:excel kt:book kt:reason kt:stage kt:log-path result started)
  (setq result (vl-catch-all-apply 'kt:open (list path)) started kt:excel)
  (xt:assert (vl-catch-all-error-p result) "locked-or-readonly-refused")
  (if expected-stage
    (progn (xt:assert (= kt:stage expected-stage) "owner-file-preflight-stage")
      (xt:assert (null started) "owner-file-before-excel-start")))
  (kt:cleanup))
(defun xt:dirty-failure (path / kt:objects kt:excel kt:book kt:reason kt:stage kt:log-path sheets ws area result)
  (kt:open path)
  (setq sheets (kt:own (vlax-get-property kt:book 'Worksheets)) ws (kt:sheet sheets "空調機器表"))
  (kt:put ws 1 1 "MUST_NOT_BE_SAVED")
  (setq area (kt:range ws 2 1 2 1))
  (vlax-put-property area 'Formula "=1/0") (kt:drop area)
  (vlax-invoke-method kt:excel 'CalculateFull)
  (xt:assert (= (length (kc:errors)) 1) "actual-formula-error-detected")
  (setq result (vl-catch-all-apply 'kt:fail '("injected failure")))
  (xt:assert (vl-catch-all-error-p result) "dirty-write-failure-injected")
  ;; Cleanup must suppress prompts even if another code path enabled alerts.
  (vlax-put-property kt:excel 'DisplayAlerts :vlax-true)
  (kt:cleanup))
(defun xt:master (path / ks:objects ks:excel ks:book ks:reason ks:stage ks:download-file ks:sheet-alias records result)
  (foreach sheet '("KUCHO_KIKI_MASTER" "KANKI_MASTER")
    (setq records (ks:read-master path sheet))
    (xt:assert (> (length records) 0) (strcat sheet "-read"))
    (xt:assert (and (null ks:objects) (null ks:book) (null ks:excel)) "master-cleanup"))
  (setq result (vl-catch-all-apply 'ks:read-master (list path "MISSING_SHEET")))
  (xt:assert (vl-catch-all-error-p result) "master-read-error-injected")
  (ks:close-excel) (ks:close-excel)
  (xt:assert (and (null ks:objects) (null ks:book) (null ks:excel)) "master-error-cleanup-idempotent"))
(xt:refused (strcat xt:directory "/busy.xlsx") "対象ファイルのロック確認")
(xt:refused (strcat xt:directory "/readonly.xlsx") nil)
(xt:export "KUCHO" (strcat xt:directory "/aircon.xlsx"))
(xt:export "KANKI" (strcat xt:directory "/vent.xlsx"))
(xt:dirty-failure (strcat xt:directory "/failure.xlsx"))
(xt:master (strcat xt:directory "/master.xlsx"))
(princ (strcat "\nEXCEL_LIFECYCLE_PASS=" (itoa xt:count))) (princ)
