;; PipeAutoCAD diagnostics and regression tests (optional).
;; Load main.LSP first, then this module. Loading defines commands only.
;; Run CAD/COM tests only on disposable drawings and workbook copies.
(vl-load-com)

;; ===== DETAILCUT arithmetic and CAD tests =====
;; Load after 09_detail_cut.lsp; run DETAILCUTTESTSOLID.
;; Pure polygon arithmetic: creates/changes no drawing entities.
(defun dc-test:area (points / prev p sum)
  (setq sum 0.0)
  (if points
    (progn
      (setq prev (last points))
      (foreach p points
        (setq sum (+ sum (- (* (car prev) (cadr p)) (* (car p) (cadr prev)))) prev p))))
  (/ (abs sum) 2.0))
(defun c:DETAILCUTTESTSOLID (/ dc:x0 dc:x1 dc:y0 dc:y1 cases entry actual failures)
  (setq dc:x0 0.0 dc:x1 10.0 dc:y0 0.0 dc:y1 10.0 failures 0
        cases '( ("inside" ((1.0 1.0 0.0) (3.0 1.0 0.0) (1.0 3.0 0.0)) 2.0)
                 ("outside" ((-3.0 1.0 0.0) (-1.0 1.0 0.0) (-1.0 3.0 0.0)) 0.0)
                 ("crossing" ((-5.0 0.0 0.0) (5.0 0.0 0.0) (5.0 10.0 0.0)) 37.5)
                 ("enclosing" ((-20.0 -20.0 0.0) (40.0 -20.0 0.0) (-20.0 40.0 0.0)) 100.0)
                 ("boundary" ((0.0 0.0 0.0) (10.0 0.0 0.0) (0.0 10.0 0.0)) 50.0)
                 ("touch only" ((-2.0 0.0 0.0) (0.0 0.0 0.0) (0.0 -2.0 0.0)) 0.0)))
  (foreach entry cases
    (setq actual (dc-test:area (dc:polygon-clip (cadr entry))))
    (if (equal actual (caddr entry) 1e-8)
      (princ (strcat "\nPASS: " (car entry)))
      (progn (setq failures (1+ failures))
             (princ (strcat "\nFAIL: " (car entry) " area=" (rtos actual 2 10))))))
  (princ (strcat "\nSOLID arithmetic tests: " (itoa failures) " failures.")) (princ))
(princ)

;; Integration check: creates temporary POINTs, processes them, then cleans up.
;; Run in a scratch drawing with an unlocked current layer; respects current UCS.
(defun c:DETAILCUTTESTPOINT (/ *error* dc:made dc:issues dc:step dc:entity-info
                             dc:x0 dc:x1 dc:y0 dc:y1 dc:eps entry e o result failures)
  (defun *error* (msg) (dc:cleanup) (princ msg) (princ))
  (setq dc:x0 0.0 dc:x1 10.0 dc:y0 0.0 dc:y1 10.0 dc:eps 1e-7 failures 0)
  (foreach entry '(("inside" (5.0 5.0 0.0) T)
                   ("outside" (11.0 5.0 0.0) nil)
                   ("edge" (0.0 5.0 0.0) T)
                   ("corner" (10.0 10.0 0.0) T)
                   ("elevated" (5.0 5.0 7.0) T))
    (setq e (entmakex (list '(0 . "POINT") (cons 10 (trans (cadr entry) 1 0)))))
    (if (null e) (exit))
    (setq o (dc:track (vlax-ename->vla-object e)) result (dc:process o 0))
    (if (and (null dc:issues)
             (if (caddr entry)
               (and (= (length result) 1) (entget e)
                    (equal (cdr (assoc 10 (entget e))) (trans (cadr entry) 1 0) 1e-8))
               (and (null result) (null (entget e)))))
      (princ (strcat "\nPASS: " (car entry)))
      (progn (setq failures (1+ failures)) (princ (strcat "\nFAIL: " (car entry))))))
  (dc:cleanup)
  (princ (strcat "\nPOINT processing tests: " (itoa failures) " failures.")) (princ))

(defun c:DETAILCUTTESTELLIPSE (/ cases entry roots param residual failures)
  (setq failures 0
        cases (list (list 5.0 0.0 0.0 2)
                    (list 5.0 0.0 3.0 2)
                    (list 3.0 4.0 2.0 2)
                    (list 5.0 0.0 6.0 0)
                    (list 0.0 5.0 5.0 1)))
  (foreach entry cases
    (setq roots (dc:unique (dc:ellipse-roots (car entry) (cadr entry) (caddr entry) 0.0 (* 2.0 pi))))
    (if (/= (length roots) (cadddr entry)) (setq failures (1+ failures)))
    (foreach param roots
      (setq residual (- (+ (* (car entry) (cos param)) (* (cadr entry) (sin param))) (caddr entry)))
      (if (> (abs residual) 1e-8) (setq failures (1+ failures)))))
  (princ (strcat "\nELLIPSE boundary-root tests: " (itoa failures) " failures.")) (princ))


;; ===== KIKISET rules and COM tests =====
;; Load 10_kikiset.lsp first; run KIKISETTEST. No Excel / drawing writes.
(defun ks:test-assert (condition label)
  (if (not condition) (progn (princ (strcat "\nFAIL: " label)) (exit))))
(defun c:KIKISETTEST (/ data)
  (ks:test-assert (= (ks:tag " model ") "MODEL") "Tag normalization")
  (ks:test-assert (not (ks:writable-p "KIKI_NO" "PAC-2")) "Protect equipment number")
  (ks:test-assert (not (ks:writable-p " location " "Office")) "Protect location")
  (ks:test-assert (not (ks:writable-p "FLOOR" "2")) "Protect placement floor")
  (ks:test-assert (not (ks:writable-p "SYSTEM" "RAC")) "Protect system")
  (ks:test-assert (not (ks:writable-p " num " "10")) "Protect number")
  (ks:test-assert (ks:writable-p "リモコン" "ワイヤレスリモコン") "Update Japanese tag")
  (ks:test-assert (ks:writable-p "FREQ" "60") "Update frequency")
  (ks:test-assert (not (ks:writable-p "NOTE" "")) "Preserve empty")
  (ks:test-assert (not (ks:writable-p "NOTE" " \t\r\n")) "Preserve whitespace")
  (ks:test-assert (not (ks:writable-p "NOTE" nil)) "Preserve missing")
  (ks:test-assert (ks:writable-p "COOL_POWER" "0") "Write numeric zero")
  (ks:test-assert (ks:writable-p "NOTE" "New note") "Write nonempty")
  (setq data '(("VOLT" . "200") ("MODEL" . "TEST") ("COOL_CAP" . "7.1")))
  (ks:test-assert (equal (assoc "MODEL" data) (assoc "MODEL" (reverse data))) "Order-independent lookup")
  (princ "\nKIKISETTEST: 14 checks passed.") (princ))

;; Optional real COM regression: creates an unsaved private workbook only.
(defun c:KIKISETCOMTEST (/ *error* ks:reason ks:objects ks:excel ks:book
                          books sheets sheet cells cell)
  (defun *error* (msg)
    (princ (strcat "\nKIKISETCOMTEST: " (if ks:reason ks:reason msg)))
    (ks:close-excel)
    (princ))
  (setq ks:excel (vlax-create-object "Excel.Application"))
  (vlax-put-property ks:excel 'DisplayAlerts :vlax-false)
  (setq books (ks:track (vlax-get-property ks:excel 'Workbooks))
        ks:book (ks:track (vlax-invoke-method books 'Add))
        sheets (ks:track (vlax-get-property ks:book 'Worksheets))
        sheet (ks:track (vlax-get-property sheets 'Item 1))
        cells (ks:track (vlax-get-property sheet 'Cells))
        cell (ks:track (vlax-get-property cells 'Item 1 1)))
  (vlax-put-property cell 'Value2 "EQUIP_TYPE")
  (ks:release cell)
  (setq ks:objects (cdr ks:objects))
  (ks:test-assert (= (ks:cell cells 1 1) "EQUIP_TYPE") "Read dispatch cell")
  (ks:test-assert (= (ks:cell cells 2 1) "") "Read empty cell")
  (ks:close-excel)
  (ks:test-assert (and (null ks:objects) (null ks:book) (null ks:excel)) "Release owned objects")
  (princ "\nKIKISETCOMTEST: 3 checks passed.")
  (princ))


;; ===== KIKISET master and filter tests =====
;; 10_kikiset.lspを先にロード。KIKISETFILTERTESTは図面・Excelを変更しない。
(defun kst:read-failure (path sheet / ks:objects ks:excel ks:book ks:reason ks:stage result reason)
  (setq result (vl-catch-all-apply 'ks:read-master (list path sheet)) reason ks:reason)
  (ks:close-excel)
  (list (vl-catch-all-error-p result) reason
        (and (null ks:objects) (null ks:excel) (null ks:book))))
(defun kst:error-tests (path / kst:count result)
  (setq kst:count 0 result (kst:read-failure (strcat path ".missing.xlsx") "KUCHO_KIKI_MASTER"))
  (kst:assert (car result) "Missing file fails")
  (kst:assert (vl-string-search "存在しません" (cadr result)) "Missing file reason")
  (kst:assert (caddr result) "Missing file cleanup")
  (setq result (kst:read-failure path "KIKISET_TEST_MISSING_SHEET"))
  (kst:assert (car result) "Missing sheet fails")
  (kst:assert (vl-string-search "シートが存在しません" (cadr result)) "Missing sheet reason")
  (kst:assert (caddr result) "Missing sheet cleanup")
  (princ (strcat "\nKIKISETERRORTEST PASSED: " (itoa kst:count))) (princ))
;; 実マスター試験: (kst:master-test "絶対パス.xlsx" "KUCHO_KIKI_MASTER")
(defun kst:assert (ok label)
  (if ok (setq kst:count (1+ kst:count))
    (progn (princ (strcat "\nFAIL: " label)) (exit))))
(defun kst:choose (title options / answer position)
  (setq answer (car kst:answers) kst:answers (cdr kst:answers))
  (cond ((member answer '(BACK CANCEL)) answer)
        ((numberp answer) answer)
        ((setq position (vl-position answer options)) (1+ position))
        (T (princ (strcat "\nUnexpected choice: " title)) (exit))))
(defun c:KIKISETFILTERTEST (/ kst:count kst:answers ks:stage ks:reason ks:selection-steps
                            headers records selected result numeric)
  (setq kst:count 0)
  (kst:assert (= (ks:value-string 12.5) "12.5") "Numeric 12.5")
  (kst:assert (= (ks:value-string 14.0) "14") "Numeric integer no unit")
  (kst:assert (= (ks:value-string 3.37) "3.37") "Numeric power precision")
  (kst:assert (= (ks:value-string 0.0) "0") "Zero is not empty")
  (kst:assert (= (ks:value-string nil) "") "Empty preserved")
  (kst:assert (= (ks:value-string "001") "001") "Text leading zeros preserved")
  (setq headers (ks:header-map '("COOL_CAP" "MODEL" "MAKER" "SYSTEM")))
  (kst:assert (= (cdr (assoc "MODEL" headers)) 1) "Header mapped by name")
  (setq records (ks:make-records '(("COOL_CAP" "MODEL" "MAKER" "SYSTEM")
                                 ("能力" "型番" "メーカー" "記号")
                                 (12.5 "M-1" "社A" "PAC")
                                 (14 "M-1" "社B" "RAC")
                                 (nil "" "" "")) headers))
  (kst:assert (= (length records) 2) "Blank MODEL row excluded")
  (kst:assert (= (car (cadr records)) 4) "Excel row identity retained")
  (kst:assert (equal (ks:unique-candidates records "MODEL") '("M-1")) "Deduplicate MODEL options")
  (kst:assert (= (length (ks:filter-records records "MAKER" "社B")) 1) "Filter current rows")
  (kst:assert (not (assoc "SYSTEM" (ks:record-data (car records)))) "Protected attribute excluded")
  (kst:assert (= (cdr (assoc "COOL_CAP" (ks:record-data (car records)))) "12.5") "Record to attribute data")
  (kst:assert (equal (ks:unique-candidates records "SERIES") '("")) "Missing classification is blank")
  (kst:assert (= (caar (ks:search-options '("A" "BB" "BC") "b")) 2) "Search keeps source number")
  (kst:assert (equal (ks:unique-candidates '((3 ("SERIES" . "")) (4 ("SERIES" . "ZR"))) "SERIES") '("" "ZR")) "Mixed blanks selectable")
  (setq ks:selection-steps '(("SYSTEM_TYPE" . "種別") ("MAKER" . "メーカー") ("MODEL" . "型番"))
        records '((3 ("SYSTEM_TYPE" . "A") ("MAKER" . "社A") ("MODEL" . "M1"))
                  (4 ("SYSTEM_TYPE" . "A") ("MAKER" . "社B") ("MODEL" . "M2"))
                  (5 ("SYSTEM_TYPE" . "B") ("MAKER" . "社B") ("MODEL" . "M3")))
        kst:answers '("A" BACK "B" "社B" "M3")
        selected (ks:select-record-ui records 'kst:choose))
  (kst:assert (= (car selected) 5) "Back restores rows from previous step")
  (kst:assert (null kst:answers) "All scripted selections consumed")
  (setq kst:answers '("A" CANCEL))
  (kst:assert (null (ks:select-record-ui records 'kst:choose)) "Cancel without a record")
  (setq ks:selection-steps '(("SERIES" . "シリーズ") ("MODEL" . "型番"))
        records '((3 ("MODEL" . "DUP")) (8 ("MODEL" . "DUP")))
        kst:answers '("DUP" BACK "DUP" 2)
        selected (ks:select-record-ui records 'kst:choose))
  (kst:assert (= (car selected) 8) "Duplicate MODEL selected by Excel row")
  (kst:assert (null kst:answers) "Empty step skipped and duplicate back works")
  (setq result (vl-catch-all-apply 'ks:header-map (list '("MAKER"))))
  (kst:assert (vl-catch-all-error-p result) "Missing MODEL detected")
  (setq result (vl-catch-all-apply 'ks:header-map (list '("MODEL" " model "))))
  (kst:assert (vl-catch-all-error-p result) "Duplicate normalized header detected")
  (setq result (vl-catch-all-apply 'ks:make-records (list '(("MODEL") ("型番")) '(("MODEL" . 0)))))
  (kst:assert (vl-catch-all-error-p result) "No equipment rows detected")
  (princ (strcat "\nKIKISETFILTERTEST PASSED: " (itoa kst:count))) (princ))

(defun kst:master-test (path sheet / *error* ks:objects ks:excel ks:book ks:stage ks:reason
                         kst:count kst:answers records selected expected entry headers values rebuilt names model started cached)
  (defun *error* (msg)
    (princ (strcat "\nKIKISETMASTERTEST FAILED: " (if ks:reason ks:reason msg)))
    (ks:close-excel) (princ))
  (setq *ks:master-cache* nil kst:count 0 records (ks:load-master path sheet))
  (setq started (getvar "MILLISECS") cached (ks:load-master path sheet))
  (princ (strcat "\nCACHE milliseconds=" (itoa (- (getvar "MILLISECS") started))))
  (kst:assert (equal records cached) "Cache returns same records")
  (kst:assert (equal (car *ks:master-cache*) (ks:cache-key path sheet)) "Cache fingerprint")
  (kst:assert (not (equal (car *ks:master-cache*) (ks:cache-key path "OTHER"))) "Sheet invalidates cache")
  (kst:assert (null (ks:cache-key (strcat path ".missing") sheet)) "Missing file cannot use cache")
  (kst:assert (and (null ks:objects) (null ks:excel) (null ks:book)) "Excel closed before selection")
  (foreach model '("PLZ-ZRMP140HF6" "PLZX-ERMP224H6" "PLZT-ERMP224L6" "PLZX-ZRMP280HF6-M" "PLZX-ZRMP140L6")
    (kst:assert (ks:filter-records records "MODEL" model) (strcat "Registered MODEL: " model)))
  (setq kst:answers '("三菱電機" "2方向天井カセット形" "同時ツイン" "140")
        selected (ks:select-record-ui records 'kst:choose))
  (kst:assert (null kst:answers) "All four actual classification choices")
  (setq expected '(("MODEL" . "PLZX-ZRMP140L6") ("COOL_CAP" . "12.5") ("HEAT_CAP" . "14")
                   ("COOL_POWER" . "3.37") ("HEAT_POWER" . "3.96")
                   ("INDOOR_MODEL" . "PL-RP71LA22") ("OUTDOOR_MODEL" . "PUZ-ZRMP140KA16")
                   ("INDOOR_QTY" . "2") ("REMOTE_MODEL" . "PAR-48MA")
                   ("LIQ_PIPE" . "9.52") ("GAS_PIPE" . "15.88")))
  (foreach entry expected
    (kst:assert (= (ks:record-value selected (car entry)) (cdr entry)) (car entry)))
  ;; 同じ実データから列を逆順にしてヘッダー変換・レコード再生成を試験する。
  (setq names (reverse (mapcar 'car (cdr selected)))
        headers (ks:header-map names)
        values (mapcar '(lambda (key) (cdr (assoc key (cdr selected)))) names)
        rebuilt (ks:make-record (car selected) values headers))
  (foreach entry expected
    (kst:assert (= (ks:record-value rebuilt (car entry)) (cdr entry)) (strcat "Reordered " (car entry))))
  (princ (strcat "\nKIKISETMASTERTEST PASSED: " (itoa kst:count)
                 " / Excel row=" (itoa (car selected)) " / MODEL=" (ks:record-value selected "MODEL")))
  (ks:close-excel) (princ))


;; ===== KIKISET registration date tests =====
;; Dependencies: load main.LSP first; shared test helpers are included below.
(defun c:KIKISETDATETEST (/ kst:count records ks:date1904 ks:stage record ks:category-id)
  (setq kst:count 0)
  (kst:assert (= (ks:registration-day "2026-09-28") (ks:registration-day "2026/09/28")) "Date formats")
  (kst:assert (= (ks:registration-day "25569") (ks:day-number 1970 1 1)) "Excel epoch")
  (kst:assert (= (ks:registration-day "25569.75") (ks:day-number 1970 1 1)) "Ignore time")
  (kst:assert (null (ks:registration-day "2026-02-29")) "Invalid leap date")
  (kst:assert (ks:registration-day "2024-02-29") "Valid leap date")
  (kst:assert (null (ks:registration-day "")) "Blank date")
  (kst:assert (null (ks:registration-day "today")) "Invalid text")
  (setq records '((3 ("MODEL" . "A") ("REGISTERED_DATE" . "2026-09-28"))
                  (4 ("MODEL" . "A") ("REGISTERED_DATE" . "2026-09-28"))
                  (5 ("MODEL" . "B") ("REGISTERED_DATE" . "2026-09-27"))
                  (6 ("MODEL" . "C"))))
  (kst:assert (= (length (ks:registered-on records (ks:day-number 2026 9 28))) 2) "Keep duplicate model rows")
  (kst:assert (null (ks:registered-on records (ks:day-number 2026 9 29))) "No matches")
  (setq ks:date1904 T record (ks:make-record 3 '(24107 "A") '(("REGISTERED_DATE" . 0) ("MODEL" . 1))))
  (kst:assert (= (ks:record-value record "REGISTERED_DATE") "25569") "1904 system conversion")
  (kst:assert (not (assoc "REGISTERED_DATE" (ks:record-data record))) "Date metadata not written")
  (kst:assert (numberp (ks:today)) "Local calendar date")
  ;; 換気でも登録日を保持して絞り込み、転記時だけ仕様属性に限定する。
  (setq ks:category-id "KANKI" ks:date1904 nil
        record (ks:make-record 3 '("VD-10ZVC7" "2026-09-28" "100")
          '(("MODEL" . 0) ("REGISTERED_DATE" . 1) ("AIRFLOW" . 2)) ))
  (kst:assert (= (caddr (assoc "KANKI" ks:profiles)) "KANKI_MASTER") "Vent sheet")
  (kst:assert (equal (ks:registered-on (list record) (ks:day-number 2026 9 28)) (list record)) "Vent today candidate")
  (kst:assert (= (ks:row-label record) "VD-10ZVC7") "Vent model only label")
  (kst:assert (not (assoc "REGISTERED_DATE" (ks:record-data record))) "Vent date not written")
  (kst:assert (= (cdr (assoc "AIRFLOW" (ks:record-data record))) "100") "Vent specifications retained")
  (princ (strcat "\nKIKISETDATETEST PASSED: " (itoa kst:count))) (princ))


;; ===== KIKISET local source tests =====
;; Dependencies: load main.LSP first; shared test helpers are included below.
;; ファイル名と旧コマンドは互換性のため保持する。
(defun kst:missing-local-source (path / ks:master-source ks:reason result)
  (setq ks:master-source (strcat path ".missing.xlsx"))
  (setq result (vl-catch-all-apply 'ks:file nil))
  (and (vl-catch-all-error-p result) ks:reason
       (vl-string-search "存在しません" ks:reason)))
(defun c:KIKISETLOCALTEST (/ *error* ks:objects ks:excel ks:book ks:download-file ks:reason ks:stage
                          kst:count records again aircon start)
  (defun *error* (msg)
    (princ (strcat "\nKIKISETLOCALTEST FAILED: " (if ks:reason ks:reason msg)))
    (ks:close-excel) (princ))
  (setq kst:count 0 *ks:master-cache* nil)
  (kst:assert (not (ks:remote-p (ks:file))) "Default source is local without selection")
  (kst:assert (= (vl-filename-base (ks:file)) "機器マスター_空調") "Expected local master name")
  (kst:assert (kst:missing-local-source (ks:file)) "Missing local master fails without remote fallback")
  (setq records (ks:load-master (ks:file) "KANKI_MASTER"))
  (kst:assert (> (length records) 0) "Local ventilation records loaded")
  (kst:assert (and (null ks:excel) (null ks:book) (null ks:objects) (null ks:download-file)) "COM cleaned without download")
  (setq start (getvar "MILLISECS") again (ks:load-master (ks:file) "KANKI_MASTER"))
  (kst:assert (equal records again) "Cached records identical")
  (princ (strcat "\nCACHE milliseconds=" (itoa (- (getvar "MILLISECS") start))))
  (kst:assert (not (equal (ks:cache-key (ks:file) "KANKI_MASTER")
                         (ks:cache-key (ks:file) "KUCHO_KIKI_MASTER"))) "Categories isolated")
  (setq aircon (ks:load-master (ks:file) "KUCHO_KIKI_MASTER"))
  (kst:assert (> (length aircon) 0) "Local air conditioning records loaded")
  (kst:assert (equal (car *ks:master-cache*) (ks:cache-key (ks:file) "KUCHO_KIKI_MASTER")) "Local file fingerprint used")
  (c:KIKISETRELOAD)
  (kst:assert (null *ks:master-cache*) "Manual reload clears remote cache")
  (princ (strcat "\nKIKISETLOCALTEST PASSED: " (itoa kst:count))) (princ))
(defun c:KIKISETSHARETEST () (c:KIKISETLOCALTEST))


;; ===== KIKISET diagnostics =====
;; 先に最新版10_kikiset.lspをAPPLOADし、このファイルをロードする。
;; KIKISETDIAGは実際の読込み経路を通すが、属性更新前に終了する。
;; 自分専用のExcelだけを使用。既存Excelの終了や図面保存は行わない。
(defun c:KIKISETDIAG (/ ks:diagnostic-log ks:diagnostic-readonly *ks:master-cache*)
  (if (not (member 'ks:trace (atoms-family 0)))
    (princ "\n先に最新版の10_kikiset.lspをAPPLOADしてください。")
    (progn
      ;; キャッシュを局所的に無効化し、通信・Excel読込みも毎回診断する。
      ;; 通常コマンドのキャッシュは診断終了後に元に戻る。
      (setq ks:diagnostic-log (vl-filename-mktemp "KIKISET-DIAG-" nil ".log")
            ks:diagnostic-readonly T
            *ks:last-diagnostic-log* ks:diagnostic-log)
      (princ (strcat "\nKIKISET 診断 D1（属性変更なし）\nログ：" ks:diagnostic-log))
      (ks:trace "DIAG D1 / FRESH MASTER / NO ATTRIBUTE WRITES")
      (c:KIKISET)
      (ks:trace "DIAG COMMAND RETURN")
      (princ (strcat "\nログ：" ks:diagnostic-log))))
  (princ))
(defun c:KIKISETDIAGLOG ()
  (if (and (boundp '*ks:last-diagnostic-log*) *ks:last-diagnostic-log*)
    (princ (strcat "\n直近の診断ログ：" *ks:last-diagnostic-log*))
    (princ "\nこの図面ではまだ診断を実行していません。"))
  (princ))
(princ "\nKIKISET診断 D1 loaded. Command: KIKISETDIAG / KIKISETDIAGLOG")
(princ)


;; ===== KIKITABLE aggregation tests =====
;; 11_kikitable.lspを先にロードし、KIKITABLETESTを実行する。
;; 集計・空配列変換の試験。図面・Excelは変更しない。
(defun ktt:assert (ok label)
  (if ok (setq ktt:passed (1+ ktt:passed))
    (progn (princ (strcat "\nFAIL: " label)) (exit))))
(defun ktt:record (key place floor note / split)
  (setq split (vl-string-search "-" key))
  (list (cons "SYSTEM" (if split (substr key 1 split) ""))
    (cons "NUM" (if split (substr key (+ split 2)) ""))
    (cons "LOCATION" place) (cons "FLOOR" floor)
    (cons "NOTE" note) '("MAKER" . "三菱電機")
    '("MODEL" . "PLZ-ZRMP112HF6") '("SYSTEM_TYPE" . "空冷ヒートポンプ式パッケージエアコン")
    '("TYPE" . "4方向天井カセット形（i-スクエアタイプ）")
    '("COOL_CAP" . "10.0") '("HEAT_CAP" . "11.2") '("COOL_POWER" . "2.17")
    '("HEAT_POWER" . "2.22") '("COMP_POWER" . "2.10") '("FAN_IN" . "0.120")
    '("FAN_OUT" . "0.060×2") '("PHASE" . "3φ") '("VOLT" . "200")
    '("リモコン" . "ワイヤードリモコン") '("FREQ" . "50")
    '("GAS_PIPE" . "15.88") '("LIQ_PIPE" . "9.52")))
(defun ktt:planned (row col / found item)
  (foreach item kt:plan
    (if (and (= row (car item)) (= col (cadr item))) (setq found (caddr item)))) found)
(defun ktt:empty-array (/ dictionary result)
  ;; AutoLISP自身では要素0のSAFEARRAYを生成できないためWindows COMから取得する。
  (setq dictionary (vlax-create-object "Scripting.Dictionary")
        result (vl-catch-all-apply 'vlax-invoke-method (list dictionary 'Items)))
  (vlax-release-object dictionary)
  (if (vl-catch-all-error-p result) (progn (princ (vl-catch-all-error-message result)) (exit)))
  result)
(defun c:KIKITABLETEST (/ ktt:passed kt:warnings kt:plan base second records groups data specs buckets i empty)
  (setq ktt:passed 0)
  (ktt:assert (null (kt:array nil)) "Missing attribute array")
  (setq empty (ktt:empty-array))
  (ktt:assert (null (kt:array (kt:unwrap empty))) "Empty attribute array")
  (ktt:assert (null (kt:array empty)) "Wrapped empty attribute array")
  (ktt:assert (equal (kt:array (vlax-safearray-fill (vlax-make-safearray vlax-vbInteger '(1 . 2)) '(7 8))) '(7 8)) "Nonempty attribute array conversion")
  (ktt:assert (equal (vl-sort '("PAC-10" "PAC-2" "RAC-1" "PAC-1" "PAC-11") 'kt:natural-less)
                      '("PAC-1" "PAC-2" "PAC-10" "PAC-11" "RAC-1")) "Natural order")
  (ktt:assert (kt:natural-less "PAC-99999999999999" "PAC-100000000000000") "Long numeric suffix")
  (ktt:assert (= (kt:floor "02") "2") "Floor normalization")
  (ktt:assert (null (kt:floor "2F")) "Reject floor unit")
  (ktt:assert (null (kt:floor "")) "Reject empty floor")
  (ktt:assert (equal (kt:number "0") 0.0) "Zero is numeric")
  (ktt:assert (null (kt:number "2.2kW")) "Reject partial number")
  (ktt:assert (null (kt:number "2.2.3")) "Reject malformed number")
  (ktt:assert (= (kt:power-text "0.060×2") "0.060kW×2") "Motor multiplication")
  (ktt:assert (= (kt:power-text "") "") "Missing power")
  (setq base (ktt:record "PAC-7" "職員室" "2" "共通備考")
        second (ktt:record "PAC-7" "会議室" "1" "共通備考")
        records (list base second base) groups (kt:group records)
        data (kt:consensus "PAC-7" records) specs (kt:spec data))
  (ktt:assert (= (length groups) 1) "Group by equipment number")
  (ktt:assert (= (length (cdar groups)) 3) "Keep duplicate instances")
  (ktt:assert (= (nth 2 specs) "冷房能力10.0kW　暖房能力11.2kW") "Capacity sentence")
  (ktt:assert (= (nth 4 specs) "圧縮機出力2.10kW　室内送風機出力0.120kW　室外送風機出力0.060kW×2") "Motor sentence")
  (ktt:assert (equal (kt:max-power "PAC-7" data) 2.22 1e-10) "Maximum power")
  (ktt:assert (= (nth 2 (kt:spec '(("COOL_CAP" . "10.0")))) "冷房能力10.0kW") "Omit missing heat phrase")
  (kt:plan-group (car groups) 0 '(("1" . 10) ("2" . 11)) 12 13)
  (ktt:assert (= (ktt:planned 6 2) "PAC-7") "Start B6")
  (ktt:assert (= (ktt:planned 6 3) "空調調和機") "Fixed equipment name without attribute")
  (ktt:assert (= (ktt:planned 6 7) "3") "Phase without phi")
  (ktt:assert (= (ktt:planned 11 5) "ワイヤードリモコン、その他付属品一式") "Remote control sentence")
  (ktt:assert (= (ktt:planned 7 4) "PLZ-ZRMP112HF6") "Model D7")
  (ktt:assert (= (ktt:planned 6 6) "職員室(2)") "Aggregate location")
  (ktt:assert (= (ktt:planned 6 11) 2) "Two units on floor 2")
  (ktt:assert (= (ktt:planned 7 10) 1) "One unit on floor 1")
  (ktt:assert (= (ktt:planned 7 12) 3) "Quantity at last location")
  (ktt:assert (= (ktt:planned 6 13) "共通備考") "Common note once")
  (ktt:assert (null (ktt:planned 7 13)) "No repeated common note")
  (setq kt:plan nil)
  (kt:plan-group (car groups) 1 '(("2" . 10) ("1" . 11)) 12 13)
  (ktt:assert (= (ktt:planned 13 2) "PAC-7") "Seven row pitch")
  (ktt:assert (= (ktt:planned 13 10) 2) "Dynamic reversed floor columns")
  (setq data (kt:consensus "PAC-7" (list base (subst '("MODEL" . "OTHER") (assoc "MODEL" base) base))))
  (ktt:assert (= (kt:get data "MODEL") "") "Conflicting model left blank")
  (ktt:assert (> (length kt:warnings) 0) "Conflict warning")
  (setq kt:plan nil kt:warnings nil records nil i 1)
  (repeat 8
    (setq records (append records (list (ktt:record "PAC-7" (strcat "Room" (itoa i)) "2" ""))) i (1+ i)))
  (kt:plan-group (car (kt:group records)) 0 '(("2" . 10)) 11 12)
  (ktt:assert (= (ktt:planned 11 6) "Room6\nRoom7\nRoom8") "All overflow locations retained")
  (ktt:assert (= (ktt:planned 11 10) "1\n1\n1") "Aligned overflow floor counts")
  (ktt:assert (= (ktt:planned 11 11) 8) "Overflow total")
  (ktt:assert (= (length kt:warnings) 1) "Overflow warning")
  (setq kt:plan nil kt:warnings nil)
  (kt:plan-group (car (kt:group (list base (subst '("NOTE" . "別備考") (assoc "NOTE" base) base))))
    0 '(("2" . 10)) 11 12)
  (ktt:assert (= (ktt:planned 6 12) "共通備考") "Note per location row 1")
  (ktt:assert (= (ktt:planned 7 12) "別備考") "Note per location row 2")
  (ktt:assert (null (kt:group (list (ktt:record "" "Room" "1" ""))))
    "Blank equipment number excluded")
  (ktt:assert (= (kt:key '(("SYSTEM" . "RAC") ("NUM" . "3"))) "RAC-3") "No fixed prefix")
  (ktt:assert (= (kt:key '(("SYSTEM" . "PAC") ("NUM" . "02"))) "PAC-02") "Preserve number spelling")
  (ktt:assert (= (kt:key '(("KIKI_NO" . "OLD") ("SYSTEM" . "PAC") ("NUM" . "2"))) "PAC-2") "Ignore legacy key")
  (ktt:assert (= (kt:get (kt:derive base) "KIKI_NO") "PAC-7") "Derived raw column")
  (ktt:assert (= (kt:get (kt:derive base) "NUM") "7") "Keep raw number")
  (ktt:assert (= (kt:get (kt:derive '(("SYSTEM" . " PAC ") ("NUM" . " 2 "))) "SYSTEM") " PAC ") "Keep raw spaces")
  (ktt:assert (= (nth 5 (kt:spec '(("リモコン" . "ワイヤレスリモコン")))) "ワイヤレスリモコン、その他付属品一式") "Wireless remote")
  (ktt:assert (= (nth 5 (kt:spec nil)) "その他付属品一式") "Missing remote no leading comma")
  (ktt:assert (= (kt:power-text "0.12") "0.12kW") "No precision adjustment")
  (ktt:assert (= (kt:capacity "4") "4.0") "Integer capacity decimal")
  (ktt:assert (= (kt:capacity "2.8") "2.8") "Decimal capacity")
  (ktt:assert (= (kt:capacity "2.86") "2.9") "Capacity rounds to one decimal")
  (ktt:assert (= (kt:capacity "0") "0.0") "Zero capacity")
  (ktt:assert (= (kt:capacity "") "") "Empty capacity")
  (ktt:assert (= (kt:phase-text "１Φ") "１") "Fullwidth number and capital phi")
  (ktt:assert (= (kt:phase-text "1φ") "1") "Lowercase phi")
  (ktt:assert (= (kt:phase-text "3") "3") "Phase without symbol unchanged")
  (setq groups (kt:group (list (ktt:record "RAC-1" "" "1" "") (ktt:record "PAC-10" "" "1" "")
                               (ktt:record "PAC-2" "" "1" "") (ktt:record "PAC-1" "" "1" ""))))
  (ktt:assert (equal (mapcar 'car groups) '("PAC-1" "PAC-2" "PAC-10" "RAC-1")) "System then numeric number")
  (setq kt:warnings nil)
  (kt:validate-record '(("SYSTEM" . "PAC") ("NUM" . "2") ("MODEL" . "M")) "TEST")
  (ktt:assert (null kt:warnings) "Optional missing attributes do not warn")
  (kt:validate-record '(("SYSTEM" . "PAC") ("NUM" . "")) "TEST")
  (ktt:assert (= (length kt:warnings) 2) "Missing number and model warn")
  (princ (strcat "\nKIKITABLETEST PASSED: " (itoa ktt:passed))) (princ))


;; ===== KIKITABLE Excel COM tests =====
;; Dependencies: load main.LSP first; shared test helpers are included below.
;; 一時フォルダに専用xlsxを生成する。実案件のExcel・図面には触れない。
(defun ktt:locked-p (path / kt:objects kt:excel kt:book kt:reason result)
  ;; 呼出し元のExcel所有権を局所変数で分離して二重更新防止を確認する。
  (setq result (vl-catch-all-apply 'kt:open (list path)))
  (kt:cleanup)
  (and (vl-catch-all-error-p result) kt:reason))
(defun ktt:fixture (/ books sheets ws other area font borders setup col text)
  (setq kt:stage "fixture Excel creation")
  (setq kt:excel (vlax-create-object "Excel.Application"))
  (vlax-put-property kt:excel 'Visible :vlax-false)
  (vlax-put-property kt:excel 'DisplayAlerts :vlax-false)
  (setq books (kt:own (vlax-get-property kt:excel 'Workbooks))
        kt:book (kt:own (vlax-invoke-method books 'Add))
        sheets (kt:own (vlax-get-property kt:book 'Worksheets))
        ws (kt:own (vlax-get-property sheets 'Item 1)))
  (vlax-put-property ws 'Name (kt:cfg 'sheet))
  (setq kt:stage "fixture headers")
  (setq col 2)
  (foreach text '("記号" "名称" "参考型番" "機器仕様" "場所" "φ" "V" "kW" "1F" "2F" "数量" "備考")
    (kt:put ws 5 col text) (setq col (1+ col)))
  (setq area (kt:range ws 6 2 12 13)
        font (kt:own (vlax-get-property area 'Font))
        borders (kt:own (vlax-get-property area 'Borders)))
  (vlax-put-property font 'Name "ＭＳ ゴシック")
  (vlax-put-property font 'Size 9)
  (vlax-put-property borders 'LineStyle 1)
  (vlax-put-property area 'RowHeight 22)
  (vlax-put-property area 'WrapText :vlax-true)
  (kt:drop borders) (kt:drop font) (kt:drop area)
  (foreach col '(2 3 7 8 9)
    (setq kt:stage "fixture merge")
    (setq area (kt:range ws 6 col 11 col))
    (vlax-invoke-method area 'Merge :vlax-false) (kt:drop area))
  (setq kt:stage "fixture page setup")
  (setq setup (kt:own (vlax-get-property ws 'PageSetup)))
  (vlax-put-property setup 'PrintArea "$A$1:$M$12")
  (kt:drop setup)
  (setq other (kt:own (vlax-invoke-method sheets 'Add)))
  (vlax-put-property other 'Name "KEEP")
  (kt:put other 1 1 "untouched")
  ws)
(defun c:KIKITABLECOMTEST (/ *error* kt:objects kt:excel kt:book kt:reason kt:stage
                           kt:cell-context kt:warnings kt:raw-tags kt:plan ktt:passed
                           path records groups sheets ws raw other area font setup result)
  (defun *error* (msg)
    (princ (strcat "\nKIKITABLECOMTEST FAILED [" (if kt:stage kt:stage "start") "]: " (if kt:reason kt:reason msg)))
    (kt:cleanup) (princ))
  (setq ktt:passed 0 kt:raw-tags (append (kt:raw-columns) '("NOTE")))
  (setq path (vl-filename-mktemp "kikitable-test-" nil ".xlsx"))
  (ktt:fixture)
  (setq kt:stage "fixture SaveAs")
  (princ "\nCOM test: SaveAs")
  (vlax-invoke-method kt:book 'SaveAs path 51 "" "" :vlax-false :vlax-false 1 2 :vlax-false 65001 1 :vlax-false)
  (ktt:assert (ktt:locked-p path) "Reject already open target workbook")
  (setq sheets (kt:own (vlax-get-property kt:book 'Worksheets)) other (kt:sheet sheets "KEEP"))
  (ktt:assert (= (kt:cell-value other 1 1) "untouched") "Keep original Excel instance open")
  (kt:cleanup)
  (princ "\nCOM test: fixture saved")
  (setq records (list (ktt:record "PAC-7" "職員室" "2" "備考")
                      (ktt:record "PAC-7" "会議室" "1" "備考")
                      (ktt:record "PAC-7" "職員室" "2" "備考")
                      (ktt:record "PAC-2" "室2" "1" "")
                      (ktt:record "PAC-10" "室10" "2" "")))
  (setq kt:stage "first open") (kt:open path)
  (kt:write-book records (kt:group records))
  (princ "\nCOM test: first write completed")
  (vlax-invoke-method kt:book 'Save)
  (kt:cleanup)
  ;; 保存後に開き直して確認する。
  (kt:open path)
  (setq sheets (kt:own (vlax-get-property kt:book 'Worksheets))
        ws (kt:sheet sheets (kt:cfg 'sheet)) raw (kt:sheet sheets (kt:cfg 'raw-sheet))
        other (kt:sheet sheets "KEEP"))
  (ktt:assert (= (kt:cell-value ws 6 2) "PAC-2") "Saved natural order first")
  (ktt:assert (= (kt:cell-value ws 13 2) "PAC-7") "Saved natural order second")
  (ktt:assert (= (kt:cell-value ws 20 2) "PAC-10") "Copied third equipment frame")
  (ktt:assert (= (kt:cell-value ws 13 6) "職員室(2)") "Saved grouped location")
  (ktt:assert (= (kt:cell-value ws 13 11) 2.0) "Saved floor count numeric")
  (ktt:assert (= (kt:cell-value ws 14 12) 3.0) "Saved total at final row")
  (ktt:assert (equal (kt:cell-value ws 13 9) 2.22 1e-10) "Saved max power")
  (ktt:assert (= (kt:cell-value ws 17 5) "圧縮機出力2.10kW　室内送風機出力0.120kW　室外送風機出力0.060kW×2") "Saved Japanese specification")
  (ktt:assert (= (kt:cell-value raw 1 1) "SYSTEM") "Raw headers")
  (ktt:assert (= (kt:cell-value raw 6 3) "PAC-10") "Every block and derived key in raw")
  (ktt:assert (= (kt:cell-value raw 6 2) "10") "Raw number retained")
  (ktt:assert (= (kt:cell-value ws 13 3) (kt:cfg 'equipment-name)) "Saved configured equipment name")
  (ktt:assert (= (kt:cell-value ws 13 7) "3") "Saved phase without phi")
  (ktt:assert (= (kt:cell-value ws 18 5) "ワイヤードリモコン、その他付属品一式") "Saved remote sentence")
  (ktt:assert (= (kt:cell-value raw 2 (1+ (vl-position "FREQ" kt:raw-tags))) "50") "Raw frequency")
  (ktt:assert (= (kt:cell-value raw 2 (1+ (vl-position "GAS_PIPE" kt:raw-tags))) "15.88") "Raw gas pipe")
  (ktt:assert (= (kt:cell-value raw 2 (1+ (vl-position "LIQ_PIPE" kt:raw-tags))) "9.52") "Raw liquid pipe")
  (ktt:assert (= (kt:cell-value other 1 1) "untouched") "Other sheet preserved")
  (setq area (kt:range ws 13 2 13 2) font (kt:own (vlax-get-property area 'Font)))
  (ktt:assert (= (kt:unwrap (vlax-get-property font 'Size)) 9.0) "Copied font size")
  (ktt:assert (= (kt:unwrap (vlax-get-property area 'RowHeight)) 22.0) "Copied row height")
  (ktt:assert (= (kt:unwrap (vlax-get-property area 'MergeCells)) :vlax-true) "Copied merged cell")
  (kt:drop font) (kt:drop area)
  (setq setup (kt:own (vlax-get-property ws 'PageSetup)))
  (ktt:assert (= (vlax-get-property setup 'PrintArea) "$A$1:$M$26") "Print area extended")
  (kt:drop setup)
  ;; 再実行で件数を減らし、旧データが帳票にもCAD_DATAにも残らないこと。
  (setq records (list (ktt:record "PAC-7" "新しい場所" "2" "=literal")))
  (kt:write-book records (kt:group records))
  (vlax-invoke-method kt:book 'Save)
  (kt:cleanup)
  (kt:open path)
  (setq sheets (kt:own (vlax-get-property kt:book 'Worksheets))
        ws (kt:sheet sheets (kt:cfg 'sheet)) raw (kt:sheet sheets (kt:cfg 'raw-sheet)))
  (ktt:assert (= (kt:cell-value ws 6 2) "PAC-7") "Rerun new first entry")
  (ktt:assert (null (kt:cell-value ws 13 2)) "Rerun removes old second entry")
  (ktt:assert (null (kt:cell-value ws 20 2)) "Rerun removes old third entry")
  (ktt:assert (null (kt:cell-value raw 3 1)) "Rerun removes stale raw data")
  (ktt:assert (= (kt:cell-value ws 6 13) "=literal") "Text is not a formula")
  ;; 保護シートへの書込み失敗では、未保存の編集を残さない。
  (vlax-invoke-method ws 'Protect "test")
  (setq result (vl-catch-all-apply 'kt:write-book (list records (kt:group records))))
  (ktt:assert (vl-catch-all-error-p result) "Protected sheet stops update")
  (kt:cleanup)
  (kt:open path)
  (setq sheets (kt:own (vlax-get-property kt:book 'Worksheets)) ws (kt:sheet sheets (kt:cfg 'sheet)))
  (ktt:assert (= (kt:cell-value ws 6 6) "新しい場所") "Failed update did not save")
  (ktt:assert (= (kt:unwrap (vlax-get-property ws 'ProtectContents)) :vlax-false) "Unsaved protection discarded")
  (kt:cleanup)
  (ktt:assert (and (null kt:objects) (null kt:book) (null kt:excel)) "COM references cleared")
  (princ (strcat "\nKIKITABLECOMTEST PASSED: " (itoa ktt:passed) "\nTest workbook: " path))
  (princ))


;; ===== KIKITABLE bulk write tests =====
;; Dependencies: load main.LSP first; shared test helpers are included below.
;; KIKITABLEBULKTEST：専用の一時Excelのみ使用。実図面・案件Excelは変更しない。
(defun c:KIKITABLEBULKTEST (/ *error* kt:objects kt:excel kt:book kt:reason kt:stage
    kt:config kt:tags kt:raw-tags kt:plan kt:warnings kt:log-path kt:cell-context
    ktt:passed ws sheets raw area records record i calculation result)
  (defun *error* (msg)
    (princ (strcat "\nKIKITABLEBULKTEST FAILED: " (if kt:reason kt:reason msg)))
    (kt:cleanup) (princ))
  (setq kt:config kt:aircon-config kt:tags kt:aircon-tags
        kt:raw-tags (append (kt:raw-columns) '("NOTE" "MISSING")) ktt:passed 0)
  (setq ws (ktt:fixture) area (kt:range ws 6 2 12 13))
  (vlax-invoke-method area 'UnMerge) (kt:drop area)
  (setq record (ktt:record "PAC-01" "=literal" "1" "=1+1")
        records (list record) calculation (kt:unwrap (vlax-get-property kt:excel 'Calculation)))
  (kt:write-book records (kt:group records))
  (ktt:assert (= (kt:unwrap (vlax-get-property kt:excel 'Calculation)) calculation) "Calculation mode restored")
  (ktt:assert (= (kt:cell-value ws 6 2) "PAC-01") "Bulk identifier retains leading zero")
  (ktt:assert (= (kt:cell-value ws 6 6) "=literal") "Bulk location is literal")
  (ktt:assert (= (kt:cell-value ws 6 13) "=1+1") "Bulk note is literal")
  (ktt:assert (= (kt:cell-value ws 6 12) 1) "Quantity stays numeric")
  (ktt:assert (equal (kt:cell-value ws 6 9) 2.22 1e-10) "Power stays numeric")
  (ktt:assert (null (kt:cell-value ws 7 2)) "Sparse cells remain blank")
  (setq area (kt:range ws 6 13 6 13))
  (ktt:assert (equal (kt:unwrap (vlax-get-property area 'HasFormula)) :vlax-false) "No injected formula")
  (kt:drop area)
  (setq sheets (kt:own (vlax-get-property kt:book 'Worksheets)) raw (kt:sheet sheets "CAD_DATA"))
  (ktt:assert (= (kt:cell-value raw 2 2) "01") "Raw number stays text")
  (ktt:assert (null (kt:cell-value raw 2 (1+ (vl-position "MISSING" kt:raw-tags)))) "Missing raw value stays blank")
  ;; 500行の境界をまたぐデータ。見出し・各個体の順序・末尾を検査。
  (setq records nil i 0)
  (repeat 1001
    (setq i (1+ i) records (cons (ktt:record "PAC-01" (itoa i) "1" "") records)))
  (kt:write-raw raw (reverse records))
  (ktt:assert (= (kt:cell-value raw 1 1) "SYSTEM") "Chunk header")
  (foreach i '(2 500 501 1000 1001 1002)
    (ktt:assert (= (kt:cell-value raw i (1+ (vl-position "LOCATION" kt:raw-tags))) (itoa (1- i)))
      (strcat "Chunk record row " (itoa i))))
  (kt:write-raw raw (list record))
  (ktt:assert (null (kt:cell-value raw 501 1)) "Rerun removes later chunks")
  ;; 結合が混在する帳票も旧検査へ進み、枠外への結合を拒否する。
  (setq area (kt:range ws 6 2 13 2))
  (vlax-invoke-method area 'Merge :vlax-false) (kt:drop area)
  (setq kt:reason nil result (vl-catch-all-apply 'kt:check-boundary (list ws 19 13)))
  (ktt:assert (and (vl-catch-all-error-p result) kt:reason) "Cross-frame merge rejected")
  (setq kt:reason nil)
  (kt:cleanup)
  (ktt:assert (and (null kt:excel) (null kt:book) (null kt:objects)) "Owned COM objects cleaned")
  (kt:cleanup)
  (princ (strcat "\nKIKITABLEBULKTEST PASSED: " (itoa ktt:passed))) (princ))


;; ===== KIKITABLE CAD tests =====
;; 新規の作業用図面だけで実行する。試験後も未使用のブロック定義は残る。
;; Dependencies: load main.LSP first; shared test helpers are included below.
(defun ktt:make-insert (name key place floor / entity pair split)
  (setq split (vl-string-search "-" key))
  (entmake (list '(0 . "INSERT") (cons 2 name) '(66 . 1) '(10 0.0 0.0 0.0)))
  (foreach pair (list (cons "SYSTEM" (substr key 1 split)) (cons "NUM" (substr key (+ split 2))) (cons "LOCATION" place)
                      (cons "FLOOR" floor) '("MODEL" . "TEST-MODEL"))
    (entmake (list '(0 . "ATTRIB") '(10 0.0 0.0 0.0) '(40 . 2.5)
                   (cons 1 (cdr pair)) (cons 2 (car pair)) '(70 . 0))))
  (entmake '((0 . "SEQEND"))) (entlast))
(defun c:KIKITABLECADTEST (/ *error* kt:config kt:objects kt:warnings kt:raw-tags
                           kt:reason ktt:passed entities entity tag records name)
  (defun *error* (msg)
    (foreach entity entities (if entity (entdel entity)))
    (kt:cleanup) (princ (strcat "\nKIKITABLECADTEST FAILED: " msg)) (princ))
  (setq name "KIKITABLE_TEST_BLOCK" ktt:passed 0)
  (if (tblsearch "BLOCK" name) (progn (princ "\n新しい作業用図面で実行してください。") (exit)))
  ;; 設定を局所的に差し替え、実案件のKUCHO_KIKIは収集しない。
  (setq kt:config (list (cons 'block name)) kt:raw-tags (kt:raw-columns))
  (entmake (list '(0 . "BLOCK") (cons 2 name) '(70 . 2) '(10 0.0 0.0 0.0)))
  (foreach tag '("SYSTEM" "NUM" "LOCATION" "FLOOR" "MODEL")
    (entmake (list '(0 . "ATTDEF") '(10 0.0 0.0 0.0) '(40 . 2.5)
                   '(1 . "") (cons 2 tag) (cons 3 tag) '(70 . 0))))
  (entmake '((0 . "ATTDEF") (10 0.0 0.0 0.0) (40 . 2.5)
             (1 . "固定メーカー") (2 . "MAKER") (3 . "MAKER") (70 . 2)))
  (entmake '((0 . "ENDBLK")))
  (setq entities (list (ktt:make-insert name "PAC-7" "職員室" "2")
                       (ktt:make-insert name "PAC-7" "会議室" "1")
                       (ktt:make-insert name "PAC-2" "室2" "1")))
  (setq records (kt:collect))
  (ktt:assert (= (length records) 3) "Collect all placed blocks")
  (ktt:assert (= (length (kt:group records)) 2) "Group collected blocks")
  (ktt:assert (= (kt:get (car records) "MODEL") "TEST-MODEL") "Read editable attributes")
  (ktt:assert (= (kt:get (car records) "MAKER") "固定メーカー") "Read constant attributes")
  (ktt:assert (null kt:warnings) "Optional missing tags allowed")
  (ktt:assert (/= (kt:get (car records) "KIKI_NO") "") "Derive key without CAD attribute")
  (foreach entity entities (if entity (entdel entity)))
  (kt:cleanup)
  (princ (strcat "\nKIKITABLECADTEST PASSED: " (itoa ktt:passed))) (princ))


;; ===== Ventilation equipment tests =====
;; Dependencies: load main.LSP first; shared test helpers are included below.
;; 図面は変更しない。COM試験には実案件ではなくテスト用コピーを渡すこと。
(defun kvt:record (place floor)
  (list '("SYSTEM" . "EF") '("NUM" . "1") (cons "LOCATION" place) (cons "FLOOR" floor)
    '("EQUIP_TYPE" . "ダクト用換気扇") '("MAKER" . "三菱電機") '("MODEL" . "VD-10ZVC7")
    '("TYPE" . "低騒音形 24時間換気機能付 定風量タイプ") '("MOUNT_TYPE" . "天井埋込")
    '("DUCT_DIA" . "100") '("AIRFLOW" . "100") '("STATIC_PRESSURE" . "90")
    '("PHASE" . "1") '("VOLT" . "100") '("POWER" . "0.0097") '("NOISE" . "23.5")))
(defun c:KANKITEST (/ ktt:passed kt:config kt:tags kt:plan kt:warnings records result data ks:category-id)
  (setq ktt:passed 0 kt:config (append kt:vent-config kt:aircon-config)
        kt:tags kt:vent-tags ks:category-id "KANKI")
  (setq data (ks:record-data (cons 3 (append (kvt:record "診察室2" "1") '(("NOTE" . "禁止"))))))
  (foreach tag '("SYSTEM" "NUM" "LOCATION" "FLOOR" "NOTE")
    (ktt:assert (not (assoc tag data)) (strcat "Protected/unlisted: " tag)))
  (ktt:assert (= (length data) 12) "Only twelve ventilation tags")
  (ktt:assert (= (cdr (assoc "PHASE" (ks:record-data '(3 ("PHASE" . "1φ"))))) "1") "Numeric phase")
  (ktt:assert (not (ks:writable-p "POWER" "")) "Empty preserves existing")
  (ktt:assert (= (cadr (kt:vent-spec (kvt:record "A" "1"))) "能力 100φ × 100m3/h × 90Pa") "Vent capacity")
  (ktt:assert (= (cadr (kt:vent-spec '(("DUCT_DIA" . "100") ("AIRFLOW" . "100")))) "能力 100φ × 100m3/h") "Missing pressure")
  (ktt:assert (= (cadr (kt:vent-spec nil)) "") "Empty spec")
  (setq records nil)
  (foreach place '("診察室2" "X線室" "トイレ" "カウンセリングルーム" "院長室" "消毒技工コーナー")
    (setq records (append records (list (kvt:record place "1")))))
  (setq result (kt:plan-vent (kt:group records) '(("1" . 10) ("2" . 11)) 12 13))
  (ktt:assert (equal (car result) '((6 6))) "Six locations use six rows")
  (ktt:assert (= (ktt:planned 6 2) "EF-1") "Derived equipment number")
  (ktt:assert (= (ktt:planned 11 12) 6) "Total at last location")
  (ktt:assert (equal (ktt:planned 6 9) 0.0097 1e-10) "Vent power")
  (setq result (kt:plan-vent (kt:group (append records (list (kvt:record "7" "2") (kvt:record "8" "2")))) '(("1" . 10) ("2" . 11)) 12 13))
  (ktt:assert (equal (car result) '((6 8))) "Eight locations expand")
  (ktt:assert (= (ktt:planned 13 11) 1) "Second floor")
  (setq result (kt:plan-vent (kt:group (list (kvt:record "同室" "1") (kvt:record "同室" "1"))) '(("1" . 10)) 11 12))
  (ktt:assert (= (ktt:planned 6 6) "同室(2)") "Same room grouped")
  (ktt:assert (= (ktt:planned 6 10) 2) "Floor count grouped")
  (ktt:assert (equal (car result) '((6 2))) "Minimum two spec rows")
  (princ (strcat "\nKANKITEST PASSED: " (itoa ktt:passed))) (princ))
(defun kvt:master-test (path / *error* ks:objects ks:excel ks:book ks:stage ks:reason
                           ks:category-id ks:selection-steps kst:answers ktt:passed records selected data model entry)
  (defun *error* (msg) (princ (strcat "\nVENT MASTER FAILED: " (if ks:reason ks:reason msg))) (ks:close-excel) (princ))
  (setq ktt:passed 0 ks:category-id "KANKI" ks:selection-steps ks:vent-steps
        records (ks:read-master path "KANKI_MASTER"))
  (foreach model '("VD-10ZVC7" "VD-15ZLC14-CS" "VD-20ZLC14-S" "VD-23ZLX14-CS" "VD-18ZP14")
    (ktt:assert (ks:filter-records records "MODEL" model) model))
  (setq kst:answers '("三菱電機" "ダクト用換気扇" "100" "100")
        selected (ks:select-record-ui records 'kst:choose) data (ks:record-data selected))
  (ktt:assert (null kst:answers) "Four ventilation choices")
  (foreach entry (ks:record-data (cons 3 (kvt:record "A" "1")))
    (ktt:assert (equal (cdr (assoc (car entry) data)) (cdr entry)) (car entry)))
  (princ (strcat "\nVENT MASTER PASSED: " (itoa ktt:passed))) (princ))
(defun kvt:book-test (path / *error* kt:objects kt:excel kt:book kt:reason kt:stage kt:cell-context kt:log-path
                         kt:config kt:tags kt:raw-tags kt:plan kt:warnings ktt:passed records sheets ws raw ac area i original-count)
  (defun *error* (msg) (princ (strcat "\nVENT BOOK FAILED: " (if kt:reason kt:reason msg))) (kt:cleanup) (princ))
  (setq kt:config (append kt:vent-config kt:aircon-config) kt:tags kt:vent-tags
        kt:raw-tags (kt:raw-columns) ktt:passed 0 records nil)
  (foreach place '("診察室2" "X線室" "トイレ" "カウンセリングルーム" "院長室" "消毒技工コーナー")
    (setq records (append records (list (kvt:record place "1")))))
  (kt:open path)
  (setq sheets (kt:own (vlax-get-property kt:book 'Worksheets)) original-count (vlax-get-property sheets 'Count))
  (kt:write-book records (kt:group records))
  (setq ws (kt:sheet sheets "機器表 (換気設備)") raw (kt:sheet sheets "CAD_DATA_KANKI"))
  (ktt:assert (= (kt:cell-value ws 6 2) "EF-1") "EF-1")
  (ktt:assert (= (kt:cell-value ws 7 5) "能力 100φ × 100m3/h × 90Pa") "Specification")
  (ktt:assert (= (kt:cell-value ws 11 11) 6) "Quantity six")
  (ktt:assert (= (kt:cell-value ws 39 2) "a") "Lower grille table untouched")
  (ktt:assert (= (vlax-get-property sheets 'Count) (1+ original-count)) "Only raw sheet added")
  ;; 40場所で印刷範囲を超え、下部表を上書きせず必要行だけ挿入する。
  (setq records nil i 1)
  (repeat 40 (setq records (cons (kvt:record (strcat "室" (itoa i)) "1") records) i (1+ i)))
  (kt:write-book (reverse records) (kt:group (reverse records)))
  (ktt:assert (= (kt:cell-value ws 45 11) 40) "Forty locations retained")
  (ktt:assert (= (kt:cell-value ws 50 2) "a") "Grille shifted by eleven rows")
  (ktt:assert (= (vlax-get-property sheets 'Count) (1+ original-count)) "Template sheet removed")
  ;; 件数減少時にも古い行が残らない。2階見出しは別の純粋テストで確認。
  (setq records (list (kvt:record "新しい場所" "1")))
  (kt:write-book records (kt:group records))
  (ktt:assert (= (kt:cell-value ws 6 6) "新しい場所") "Rerun location")
  (ktt:assert (null (kt:cell-value ws 9 6)) "Stale location removed")
  (ktt:assert (null (kt:cell-value raw 3 1)) "Stale raw removed")
  (ktt:assert (= (kt:cell-value ws 50 2) "a") "Rerun retains lower table")
  (vlax-invoke-method kt:book 'Save)
  (kt:cleanup)
  (princ (strcat "\nVENT BOOK PASSED: " (itoa ktt:passed))) (princ))
(defun kvt:aircon-book-test (path / *error* kt:objects kt:excel kt:book kt:reason kt:stage kt:cell-context kt:log-path
                               kt:config kt:tags kt:raw-tags kt:plan kt:warnings ktt:passed records sheets ws)
  (defun *error* (msg) (princ (strcat "\nAIRCON BOOK FAILED: " (if kt:reason kt:reason msg))) (kt:cleanup) (princ))
  (setq kt:config kt:aircon-config kt:tags kt:aircon-tags kt:raw-tags (kt:raw-columns) ktt:passed 0
        records (list (ktt:record "PAC-7" "室1" "1" "") (ktt:record "PAC-7" "室2" "1" "")))
  (kt:open path) (kt:write-book records (kt:group records))
  (setq sheets (kt:own (vlax-get-property kt:book 'Worksheets)) ws (kt:sheet sheets "機器表 (空調設備)"))
  (ktt:assert (= (kt:cell-value ws 6 2) "PAC-7") "Aircon number")
  (ktt:assert (= (kt:cell-value ws 8 5) "冷房能力10.0kW　暖房能力11.2kW") "Aircon capacities")
  (ktt:assert (= (kt:cell-value ws 6 7) "3") "Aircon phase")
  (ktt:assert (= (kt:cell-value ws 7 11) 2) "Aircon quantity")
  (vlax-invoke-method kt:book 'Save) (kt:cleanup)
  (princ (strcat "\nAIRCON BOOK PASSED: " (itoa ktt:passed))) (princ))


;; ===== Heat exchange ventilation tests =====
;; Dependencies: load main.LSP first; shared test helpers are included below.
(defun kht:record ()
  '(("SYSTEM" . "HEX") ("NUM" . "1") ("EQUIP_TYPE" . "全熱交換器")
    ("MAKER" . "三菱電機") ("MODEL" . "VL-200ZSD3") ("TYPE" . "天井埋込形")
    ("DUCT_DIA" . "100") ("AIRFLOW" . "48") ("STATIC_PRESSURE" . "20")
    ("TEMP_EX_EFF" . "76") ("ENTHALPY_HEAT_EFF" . "63") ("ENTHALPY_COOL_EFF" . "58")
    ("PHASE" . "1") ("VOLT" . "100") ("POWER" . "0.059") ("LOCATION" . "廊下") ("FLOOR" . "1")))
(defun c:KANKIHEXTEST (/ kt:config kt:tags kt:plan kt:warnings ks:category-id ktt:passed data specs layout entry)
  (setq kt:config (append kt:vent-config kt:aircon-config) kt:tags kt:vent-tags
        ks:category-id "KANKI" ktt:passed 0 data (kht:record) specs (kt:vent-spec data))
  (ktt:assert (equal specs '("天井埋込形" "能力 100φ × 48m3/h × 20Pa 温度交換効率 76%" "その他付属品一式")) "HEX three lines")
  (ktt:assert (= (cadr (kt:vent-spec (vl-remove (assoc "STATIC_PRESSURE" data) data))) "能力 100φ × 48m3/h 温度交換効率 76%") "Missing pressure")
  (ktt:assert (= (cadr (kt:vent-spec (vl-remove (assoc "TEMP_EX_EFF" data) data))) "能力 100φ × 48m3/h × 20Pa") "Missing efficiency")
  (ktt:assert (= (caddr (kt:vent-spec (cons '("ACCESSORY" . "天井パネル、リモコン") data))) "天井パネル、リモコン") "Explicit accessory")
  (ktt:assert (equal (kt:vent-spec '(("EQUIP_TYPE" . "全熱交換器"))) '("" "" "その他付属品一式")) "Empty fields do not produce units")
  (foreach entry '(("TEMP_EX_EFF" . "76") ("ENTHALPY_HEAT_EFF" . "63") ("ENTHALPY_COOL_EFF" . "58"))
    (ktt:assert (equal (assoc (car entry) (ks:record-data (cons 3 data))) entry) (car entry)))
  (ktt:assert (assoc "ACCESSORY" (ks:record-data '(3 ("ACCESSORY" . "リモコン")))) "Accessory mapping")
  (setq layout (kt:plan-vent (kt:group (list data)) '(("1" . 10)) 11 12))
  (ktt:assert (equal (car layout) '((6 3))) "Three rows plus gap")
  (foreach entry '(((6 2) . "HEX-1") ((6 3) . "全熱交換器") ((6 4) . "三菱電機")
                  ((7 4) . "VL-200ZSD3") ((6 6) . "廊下") ((6 7) . "1") ((6 8) . "100")
                  ((6 10) . 1) ((6 11) . 1) ((8 5) . "その他付属品一式"))
    (ktt:assert (equal (ktt:planned (caar entry) (cadar entry)) (cdr entry)) (vl-princ-to-string (car entry))))
  (ktt:assert (equal (ktt:planned 6 9) 0.059 1e-10) "HEX power")
  (setq layout (kt:plan-vent (kt:group (list (kvt:record "A" "1") data)) '(("1" . 10)) 11 12))
  (ktt:assert (equal (car layout) '((6 2) (9 3))) "Mixed EF unchanged and HEX expanded")
  (ktt:assert (= (ktt:planned 10 4) "VL-200ZSD3") "Mixed model row")
  (princ (strcat "\nKANKIHEXTEST PASSED: " (itoa ktt:passed))) (princ))
(defun kht:book-test (path / *error* kt:objects kt:excel kt:book kt:reason kt:stage kt:cell-context kt:log-path
                           kt:config kt:tags kt:raw-tags kt:plan kt:warnings ktt:passed records sheets ws)
  (defun *error* (msg) (princ (strcat "\nHEX BOOK FAILED: " (if kt:reason kt:reason msg))) (kt:cleanup) (princ))
  (setq kt:config (append kt:vent-config kt:aircon-config) kt:tags kt:vent-tags
        kt:raw-tags (kt:raw-columns) ktt:passed 0 records (list (kht:record)))
  (kt:open path) (kt:write-book records (kt:group records))
  (setq sheets (kt:own (vlax-get-property kt:book 'Worksheets)) ws (kt:sheet sheets "機器表 (換気設備)"))
  (ktt:assert (= (kt:cell-value ws 6 2) "HEX-1") "Excel symbol")
  (ktt:assert (= (kt:cell-value ws 7 4) "VL-200ZSD3") "Excel model")
  (ktt:assert (= (kt:cell-value ws 7 5) "能力 100φ × 48m3/h × 20Pa 温度交換効率 76%") "Excel efficiency")
  (ktt:assert (= (kt:cell-value ws 8 5) "その他付属品一式") "Excel accessories")
  (ktt:assert (null (kt:cell-value ws 9 5)) "Excel gap")
  (ktt:assert (= (kt:cell-value ws 39 2) "a") "Lower table preserved")
  (vlax-invoke-method kt:book 'Save) (kt:cleanup)
  (princ (strcat "\nHEX BOOK PASSED: " (itoa ktt:passed))) (princ))


;; ===== GARARITABLE tests =====
(defun c:GARARIMASTERTEST (/ garari:reason garari:issues garari:test-passed headers matrix rows result)
  (setq garari:test-passed 0
        headers '("MODEL" "MANUFACTURER" "DIA" "SPEC_NOTE" "APPROVED" "SOURCE_URL" "CHECKED_DATE")
        matrix (list headers '("品番" "メーカー" "径" "仕様" "承認" "URL" "日付")
          '("TEST-001" "Maker" 100 "Note" 1 "" "2026-10-11")
          '(nil nil nil nil nil nil nil))
        rows (garari:matrix-rows matrix "room" "fixture"))
  (garari:test-assert (= (length rows) 1) "Two header rows and blank rows skipped")
  (garari:test-assert (= (garari:get (car rows) "DIA") "100") "Numeric diameter converted")
  (garari:test-assert (= (garari:get (car rows) "APPROVED") "1") "Numeric approval converted")
  (garari:test-assert (= (garari:get (car rows) "SOURCE_URL") "") "Empty cell retained")
  (garari:test-assert (= (garari:master-value "001") "001") "Literal identifier retained")
  (setq rows (garari:matrix-rows (mapcar 'reverse matrix) "room" "reordered"))
  (garari:test-assert (= (garari:get (car rows) "MODEL") "TEST-001") "Column order independent")
  (setq result (vl-catch-all-apply 'garari:matrix-rows (list '(("MODEL") ("品番") ("TEST")) "room" "missing")))
  (garari:test-assert (vl-catch-all-error-p result) "Missing required column rejected")
  (setq result (vl-catch-all-apply 'garari:matrix-rows (list (list (append headers '("MODEL"))) "room" "duplicate")))
  (garari:test-assert (vl-catch-all-error-p result) "Duplicate header rejected")
  (setq result (vl-catch-all-apply 'garari:matrix-rows (list (list headers (cadr matrix) '("TEST" "Maker" 100 "" 2 "" "")) "room" "approval")))
  (garari:test-assert (vl-catch-all-error-p result) "Invalid approval rejected")
  (setq result (vl-catch-all-apply 'garari:matrix-rows (list (list headers (cadr matrix)) "room" "empty")))
  (garari:test-assert (vl-catch-all-error-p result) "Empty equipment rows rejected")
  (setq garari:reason nil result (vl-catch-all-apply 'garari:read-masters (list (strcat (garari:master-path) ".missing.xlsx"))))
  (garari:test-assert (vl-catch-all-error-p result) "Missing workbook rejected")
  (garari:test-assert (and (null garari:excel) (null garari:book) (null garari:objects)) "Failed read ownership cleaned")
  (princ (strcat "\nGARARIMASTERTEST PASS=" (itoa garari:test-passed))) (princ))
;; Load 12_garari_table.lsp first. GARARITABLETEST is read-only (no DWG/Excel writes).
(defun garari:test-assert (ok label)
  (if ok (setq garari:test-passed (1+ garari:test-passed))
    (progn (princ (strcat "\nFAIL: " label)) (exit))))
(defun garari:test-record (raw handle floor master rooms / trace)
  (setq trace (list '("ISSUES" . nil) '("DWG" . "fixture.dwg") (cons "HANDLE" handle)
    '("NAME" . "GARARI") '("LAYER" . "fixture") (cons "POINT" (list (atof handle) 0.0 0.0))
    (cons "FLOOR" floor) (cons "SELECT_FLOOR" floor)))
  (garari:record raw trace master rooms garari:config))
(defun c:GARARITABLETEST (/ *error* garari:reason garari:file garari:test-passed garari:issues masters master rooms base a b c d g rows floors plan r norm raw)
  (defun *error* (msg) (if garari:file (close garari:file))
    (princ (strcat "\nTEST ERROR: " (if garari:reason garari:reason msg))) (princ))
  (setq garari:test-passed 0)
  (setq masters (garari:read-masters (garari:master-path))
    master (car masters) rooms (cadr masters)
    base '(("GARARI" . "2") ("DIA" . "150") ("FD" . "あり") ("SHAPE" . "深型") ("MATERIAL" . "SUS") ("MESH" . "あり") ("ROOM" . "なし")))
  (garari:test-assert (null garari:issues) "Initial masters have unique keys")
  (foreach raw '("150" "φ150" "Φ150" "150φ" "150mm" "　１５０　") (garari:test-assert (= (garari:dia raw) "150") "Diameter forms"))
  (foreach raw '("150×100" "150.5" "150abc" "0" "-150" "150mmmm" "") (garari:test-assert (= (garari:dia raw) "") "Reject bad diameters"))
  (garari:test-assert (equal (garari:csv-line "a,\"b,c\",\"d\"\"e\",") '("a" "b,c" "d\"e" "")) "CSV commas, quotes and empty last field")
  (setq a (garari:test-record base "1" "1F" master rooms))
  (garari:test-assert (= (garari:get (garari:get a "OUTDOOR") "MODEL") "P-18VSQD4") "A ordinary model")
  (garari:test-assert (= (garari:state a) "正常") "A normal state")
  (setq b (garari:test-record base "2" "1F" master rooms) c (garari:test-record base "3" "2F" master rooms)
    g (garari:aggregate (list a b c)) floors (garari:floors (list a b c)) plan (garari:table-plan g floors))
  (garari:test-assert (= (length g) 1) "B one group")
  (garari:test-assert (equal (nth 1 (car plan)) (list "2" "ガラリ" "三菱電機" (garari:spec a) 2 1 3 "深型")) "B floor quantities and total once")
  (garari:test-assert (= (length (car plan)) 4) "Outdoor manufacturer/model/spacer rows")
  (setq r (garari:test-record (cons '("SOUND" . "あり") base) "4" "1F" master rooms))
  (garari:test-assert (= (garari:get (garari:get r "OUTDOOR") "MODEL") "P-18VSSQD3") "C explicit sound")
  (setq raw (garari:set (garari:set (garari:set (garari:set base "GARARI" "a") "DIA" "100") "FD" "なし") "ROOM" "ｐ-１３ｗｑｕ")
    d (garari:test-record raw "5" "1F" master rooms) plan (garari:table-plan (garari:aggregate (list d)) '("1F")))
  (garari:test-assert (= (garari:get (garari:get d "OUTDOOR") "MODEL") "P-13VSQ4") "D outdoor")
  (garari:test-assert (= (garari:get (garari:get d "INDOOR") "MODEL") "P-13WQU") "D normalized indoor")
  (garari:test-assert (= (nth 5 (nth 1 (car plan))) 1) "D set is one quantity")
  (garari:test-assert (= (length (car plan)) 5) "D indoor on separate row")
  (setq r (garari:test-record (garari:set (garari:set raw "SHAPE" "平型") "ROOM" "なし") "6" "1F" master rooms))
  (garari:test-assert (= (garari:get (garari:get r "OUTDOOR") "MODEL") "BSW100SB10M") "E flat SB")
  (setq r (garari:test-record (garari:set (garari:set base "SHAPE" "平型") "MESH" "なし") "7" "1F" master rooms))
  (garari:test-assert (null (garari:get r "OUTDOOR")) "F unregistered model never fabricated")
  (setq r (garari:test-record (garari:set base "DIA" "100") "8" "1F" master rooms)
    g (garari:aggregate (garari:cross-check (list a r))))
  (garari:test-assert (= (length g) 2) "G same symbol different spec stays separate")
  (garari:test-assert (= (garari:state (cadar g)) "要確認") "G both conflict warning")
  (setq r (garari:test-record (garari:set base "GARARI" "1") "9" "1F" master rooms))
  (garari:test-assert (= (length (garari:aggregate (list a r))) 2) "H symbols separate")
  (setq r (garari:test-record (garari:set base "ROOM" "あり") "10" "1F" master rooms))
  (garari:test-assert (= (garari:state r) "エラー") "I missing indoor model")
  (foreach raw (list (garari:set base "ROOM" "") (garari:set base "DIA" "150×100")
    (garari:set base "FD" "") (vl-remove-if '(lambda (x) (= (car x) "ROOM")) base))
    (setq r (garari:test-record raw "11" "1F" master rooms))
    (garari:test-assert (= (garari:state r) "エラー") "J invalid input retained")
    (garari:test-assert (= (length (garari:aggregate (list r))) 1) "J quantity retained"))
  (setq r (garari:test-record (garari:set base "GARARI" "01") "12" "1F" master rooms))
  (garari:test-assert (= (garari:symbol r) "01") "M leading zeros preserved")
  (setq r (garari:test-record base "13" "1F" (append master master) rooms))
  (garari:test-assert (null (garari:get r "OUTDOOR")) "N multiple approved matches not selected")
  (garari:test-assert (= (garari:state r) "エラー") "N master conflict state")
  (setq r (garari:test-record (garari:set base "ROOM" "P-13WQU") "14" "1F" master rooms))
  (garari:test-assert (= (garari:state r) "エラー") "O indoor dia mismatch")
  (garari:test-assert (null (garari:get r "INDOOR")) "O do not display matched indoor specs")
  (garari:test-assert (equal (garari:floors (mapcar '(lambda (f) (garari:test-record base f f master rooms)) '("other2" "2F" "B1F" "1F" "B2F" "other1" "RF" "階未設定")))
    '("B2F" "B1F" "1F" "2F" "RF" "other2" "other1" "階未設定")) "Floor order including stable unknowns")
  (setq norm (garari:normalize (garari:set base "MATERIAL" "SUS316") garari:config))
  (garari:test-assert (= (garari:get norm "MATERIAL") "SUS316") "Do not replace SUS316")
  (setq r (garari:test-record (garari:set base "GARARI" "") "15" "1F" master rooms))
  (garari:test-assert (= (garari:symbol r) "未設定@15") "Blank symbol surrogate")
  (setq r (garari:test-record (cons '("FLOOR" . "2F") base) "16" "1F" master rooms))
  (garari:test-assert (= (garari:get r "FLOOR") "2F") "FLOOR attribute precedence")
  (garari:test-assert (= (length (car (garari:raw-data (list a)))) (length (cadr (garari:raw-data (list a))))) "CAD_DATA rectangular")
  (princ (strcat "\nGARARITABLETEST PASS=" (itoa garari:test-passed))) (princ))

;; Creates ONLY a dedicated test Excel app and new file in the test directory.
(defun garari:test-write-hidden (path records cfg / garari:config)
  (setq garari:config (garari:set cfg 'show-result nil))
  (garari:write-xlsx path records (garari:aggregate records) (garari:floors records) '(("TEST" "fixture")) nil))
(defun c:GARARITABLECOMTEST (/ *error* garari:stage garari:objects garari:excel garari:book garari:handed garari:temp garari:saved garari:file garari:reason garari:issues masters master rooms base records path books)
  (defun *error* (msg) (garari:cleanup) (princ (strcat "\nCOMTEST ERROR: " (if garari:stage garari:stage "start") ": " (if garari:reason garari:reason msg))) (princ))
  (setq masters (garari:read-masters (garari:master-path))
    master (car masters) rooms (cadr masters)
    base '(("GARARI" . "01") ("DIA" . "150") ("FD" . "あり") ("SHAPE" . "深型") ("MATERIAL" . "SUS") ("MESH" . "あり") ("ROOM" . "なし")))
  (setq records (list (garari:test-record base "1" "1F" master rooms)
    (garari:test-record base "2" "1F" master rooms) (garari:test-record base "3" "2F" master rooms)
    (garari:test-record (garari:set (garari:set (garari:set base "GARARI" "a") "DIA" "100") "ROOM" "P-13WQU") "4" "1F" master rooms)
    (garari:test-record (garari:set (garari:set base "GARARI" "=1+1") "SHAPE" "平型") "5" "2F" master rooms)))
  (vl-mkdir (strcat garari:directory "/日本語 試験"))
  (setq path (strcat garari:directory "/日本語 試験/acceptance.xlsx"))
  (garari:test-write-hidden path records garari:config)
  (setq books (garari:own (vlax-get-property garari:excel 'Workbooks))
    garari:book (garari:own (garari:open-book books (vl-string-translate "/" "\\" path))))
  (garari:close-book garari:book) (setq garari:book nil)
  (garari:cleanup) (princ "\nGARARITABLECOMTEST PASS") (princ))

;; Only on a disposable empty DWG: creates fixture block GARARI, not production data.
(defun c:GARARITABLECADTEST (/ *error* garari:reason garari:issues garari:file garari:test-passed raw pair tag flag e masters master rooms r)
  (defun *error* (msg) (if garari:file (close garari:file))
    (princ (strcat "\nCADTEST ERROR: " (if garari:reason garari:reason msg))) (princ))
  (if (tblsearch "BLOCK" "GARARI") (garari:fail "CADTESTはGARARI定義のない検証専用DWGで実行してください。"))
  (setq garari:test-passed 0 raw '(("GARARI" . "2") ("DIA" . "150") ("FD" . "あり") ("SHAPE" . "深型") ("MATERIAL" . "SUS") ("MESH" . "あり") ("ROOM" . "なし")))
  (entmake '((0 . "BLOCK") (2 . "GARARI") (70 . 2) (10 0.0 0.0 0.0)))
  (foreach pair raw
    (setq tag (car pair) flag (cond ((= tag "ROOM") 2) ((= tag "DIA") 1) (T 0)))
    (entmake (list '(0 . "ATTDEF") '(10 0.0 0.0 0.0) '(40 . 2.5) (cons 1 (cdr pair)) (cons 2 tag) (cons 3 tag) (cons 70 flag))))
  (entmake '((0 . "ENDBLK")))
  (entmake '((0 . "INSERT") (2 . "GARARI") (66 . 1) (10 10.0 20.0 0.0)))
  (foreach pair raw
    (if (/= (car pair) "ROOM") (entmake (list '(0 . "ATTRIB") '(10 10.0 20.0 0.0) '(40 . 2.5) (cons 1 (cdr pair)) (cons 2 (car pair)) (cons 70 (if (= (car pair) "DIA") 1 0))))))
  (entmake '((0 . "SEQEND"))) (setq e (entlast))
  (garari:test-assert (garari:target e) "Direct model GARARI is accepted")
  (setq masters (garari:read-masters (garari:master-path))
    master (car masters) rooms (cadr masters)
    r (garari:extract e "1F" master rooms garari:config))
  (garari:test-assert (= (garari:get (garari:get r "RAW") "DIA") "150") "Invisible DIA read")
  (garari:test-assert (= (garari:get (garari:get r "RAW") "ROOM") "なし") "Constant ROOM read")
  (garari:test-assert (= (garari:get (garari:get r "OUTDOOR") "MODEL") "P-18VSQD4") "Extracted ordinary model")
  (garari:test-assert (= (garari:state r) "正常") "Extracted valid state")
  (garari:test-assert (equal (garari:get r "POINT") '(10.0 20.0 0.0)) "WCS insertion trace")
  (princ (strcat "\nGARARITABLECADTEST PASS=" (itoa garari:test-passed))) (princ))

(princ "\nPipeAutoCAD diagnostics/tests loaded. Tests run only when invoked.")
(princ)
