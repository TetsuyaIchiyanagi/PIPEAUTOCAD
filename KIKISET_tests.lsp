;; Load 10_kikiset.lsp first; run KIKISETTEST. No Excel / drawing writes.
(defun ks:test-assert (condition label)
  (if (not condition) (progn (princ (strcat "\nFAIL: " label)) (exit))))
(defun c:KIKISETTEST (/ data)
  (ks:test-assert (= (ks:tag " model ") "MODEL") "Tag normalization")
  (ks:test-assert (not (ks:writable-p "KIKI_NO" "PAC-2")) "Protect equipment number")
  (ks:test-assert (not (ks:writable-p " location " "Office")) "Protect location")
  (ks:test-assert (not (ks:writable-p "FLOOR" "2")) "Protect placement floor")
  (ks:test-assert (not (ks:writable-p "SYSTEM" "RAC")) "Protect system")
  (ks:test-assert (not (ks:writable-p " num " "10")) "Protect number")
  (ks:test-assert (ks:writable-p "リモコン" "ワイヤレスリモコン") "Update Japanese tag")
  (ks:test-assert (ks:writable-p "FREQ" "60") "Update frequency")
  (ks:test-assert (not (ks:writable-p "NOTE" "")) "Preserve empty")
  (ks:test-assert (not (ks:writable-p "NOTE" " \t\r\n")) "Preserve whitespace")
  (ks:test-assert (not (ks:writable-p "NOTE" nil)) "Preserve missing")
  (ks:test-assert (ks:writable-p "COOL_POWER" "0") "Write numeric zero")
  (ks:test-assert (ks:writable-p "NOTE" "New note") "Write nonempty")
  (setq data '(("VOLT" . "200") ("MODEL" . "TEST") ("COOL_CAP" . "7.1")))
  (ks:test-assert (equal (assoc "MODEL" data) (assoc "MODEL" (reverse data))) "Order-independent lookup")
  (princ "\nKIKISETTEST: 14 checks passed.") (princ))

;; Optional real COM regression: creates an unsaved private workbook only.
(defun c:KIKISETCOMTEST (/ *error* ks:reason ks:objects ks:excel ks:book
                          books sheets sheet cells cell)
  (defun *error* (msg)
    (princ (strcat "\nKIKISETCOMTEST: " (if ks:reason ks:reason msg)))
    (ks:close-excel)
    (princ))
  (setq ks:excel (vlax-create-object "Excel.Application"))
  (vlax-put-property ks:excel 'DisplayAlerts :vlax-false)
  (setq books (ks:track (vlax-get-property ks:excel 'Workbooks))
        ks:book (ks:track (vlax-invoke-method books 'Add))
        sheets (ks:track (vlax-get-property ks:book 'Worksheets))
        sheet (ks:track (vlax-get-property sheets 'Item 1))
        cells (ks:track (vlax-get-property sheet 'Cells))
        cell (ks:track (vlax-get-property cells 'Item 1 1)))
  (vlax-put-property cell 'Value2 "EQUIP_TYPE")
  (ks:release cell)
  (setq ks:objects (cdr ks:objects))
  (ks:test-assert (= (ks:cell cells 1 1) "EQUIP_TYPE") "Read dispatch cell")
  (ks:test-assert (= (ks:cell cells 2 1) "") "Read empty cell")
  (ks:close-excel)
  (ks:test-assert (and (null ks:objects) (null ks:book) (null ks:excel)) "Release owned objects")
  (princ "\nKIKISETCOMTEST: 3 checks passed.")
  (princ))
