;; Read/update only an unsaved disposable COPY, never the reference workbook.
(setq kh:count 0)
(defun *error* (msg) (princ (strcat "\nREGRESSION_ERROR: " msg)) (kt:cleanup) (princ))
(defun kh:assert (ok label)
  (if (not ok) (progn (princ (strcat "\nFAIL: " label)) (exit)))
  (setq kh:count (1+ kh:count)) (princ (strcat "\nPASS: " label)))
(kh:assert (kc:header-equal "採用機器の換気能力" "採用機器の換気能力") "exact-heading")
(kh:assert (kc:header-equal " 採用機器の\r\n換気能力　\t" "採用機器の換気能力") "header-layout-whitespace")
(kh:assert (kc:header-equal (strcat (chr 65279) "採用機器の" (chr 160) (chr 8203) "換気能力") "採用機器の換気能力") "header-invisible-formatting")
(kh:assert (not (kc:header-equal "必要換気量" "採用機器の換気能力")) "different-heading-refused")
(kh:assert (not (kc:header-equal "" "採用機器の換気能力")) "empty-heading-refused")
(kh:assert (not (equal (kc:key '(("FLOOR" . "1") ("LOCATION" . "事 務室")))
  (kc:key '(("FLOOR" . "1") ("LOCATION" . "事務室"))))) "room-key-whitespace-stays-distinct")
(kt:open kr:fixture)
(setq kh:sheets (kt:own (vlax-get-property kt:book 'Worksheets)) kh:ws (kt:sheet kh:sheets kc:sheet-name))
(kh:assert (not (vl-catch-all-error-p (vl-catch-all-apply 'kc:headers (list kh:ws)))) "reference-original-headers-pass")
(setq kh:label " 採用機器の\r\n換気能力　")
(kt:put kh:ws 3 18 kh:label)
(kt:put kh:ws 3 16 "決定換気量")
(kt:put kh:ws 3 22 "送風機形式")
(kh:assert (not (vl-catch-all-error-p (vl-catch-all-apply 'kc:headers (list kh:ws)))) "merged-R3-line-breaks-pass")
(kh:assert (= (kt:cell-value kh:ws 3 18) kh:label) "validation-does-not-rewrite-heading")
(kt:put kh:ws 3 18 "必要換気量")
(setq kt:reason nil kh:result (vl-catch-all-apply 'kc:headers (list kh:ws)))
(kh:assert (and (vl-catch-all-error-p kh:result) (wcmatch kt:reason "*R3*期待=*採用機器の換気能力*実際=*必要換気量*結合範囲=*$R$3:$S$3*")) "mismatch-reports-expected-actual-and-merge")
(kt:clear kh:ws 3 18 3 19)
(setq kt:reason nil kh:result (vl-catch-all-apply 'kc:headers (list kh:ws)))
(kh:assert (and (vl-catch-all-error-p kh:result) (wcmatch kt:reason "*R3*")) "empty-R3-not-bypassed")
(kt:put kh:ws 3 18 "採用機器の換気能力")
(kt:put kh:ws 4 18 "静圧") (kt:put kh:ws 4 19 "風量")
(setq kt:reason nil kh:result (vl-catch-all-apply 'kc:headers (list kh:ws)))
(kh:assert (and (vl-catch-all-error-p kh:result) (wcmatch kt:reason "*R4*")) "swapped-airflow-pressure-columns-refused")
(kt:cleanup)
(princ (strcat "\nKANKI_HEADER_PASS=" (itoa kh:count))) (princ)
