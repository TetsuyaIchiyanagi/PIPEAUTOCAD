;; Load garari_table.lsp first. GARARITABLETEST is read-only (no DWG/Excel writes).
(defun garari:test-assert (ok label)
  (if ok (setq garari:test-passed (1+ garari:test-passed))
    (progn (princ (strcat "\nFAIL: " label)) (exit))))
(defun garari:test-record (raw handle floor master rooms / trace)
  (setq trace (list '("ISSUES" . nil) '("DWG" . "fixture.dwg") (cons "HANDLE" handle)
    '("NAME" . "GARARI") '("LAYER" . "fixture") (cons "POINT" (list (atof handle) 0.0 0.0))
    (cons "FLOOR" floor) (cons "SELECT_FLOOR" floor)))
  (garari:record raw trace master rooms garari:config))
(defun c:GARARITABLETEST (/ *error* garari:reason garari:file garari:test-passed garari:issues master rooms base a b c d g rows floors plan r norm raw)
  (defun *error* (msg) (if garari:file (close garari:file))
    (princ (strcat "\nTEST ERROR: " (if garari:reason garari:reason msg))) (princ))
  (setq garari:test-passed 0)
  (setq master (garari:read-master (strcat garari:directory "/garari_master.csv") "outdoor")
    rooms (garari:read-master (strcat garari:directory "/room_master.csv") "room")
    base '(("GARARI" . "2") ("DIA" . "150") ("FD" . "あり") ("SHAPE" . "深型") ("MATERIAL" . "SUS") ("MESH" . "あり") ("ROOM" . "なし")))
  (garari:test-assert (null garari:issues) "Initial masters have unique keys")
  (foreach raw '("150" "φ150" "Φ150" "150φ" "150mm" "　１５０　") (garari:test-assert (= (garari:dia raw) "150") "Diameter forms"))
  (foreach raw '("150×100" "150.5" "150abc" "0" "-150" "150mmmm" "") (garari:test-assert (= (garari:dia raw) "") "Reject bad diameters"))
  (garari:test-assert (equal (garari:csv-line "a,\"b,c\",\"d\"\"e\",") '("a" "b,c" "d\"e" "")) "CSV commas, quotes and empty last field")
  (setq a (garari:test-record base "1" "1F" master rooms))
  (garari:test-assert (= (garari:get (garari:get a "OUTDOOR") "MODEL") "P-18VSQD4") "A ordinary model")
  (garari:test-assert (= (garari:state a) "正常") "A normal state")
  (setq b (garari:test-record base "2" "1F" master rooms) c (garari:test-record base "3" "2F" master rooms)
    g (garari:aggregate (list a b c)) floors (garari:floors (list a b c)) plan (garari:table-plan g floors))
  (garari:test-assert (= (length g) 1) "B one group")
  (garari:test-assert (equal (nth 1 (car plan)) (list "2" "ガラリ" "三菱電機" (garari:spec a) 2 1 3 "深型")) "B floor quantities and total once")
  (garari:test-assert (= (length (car plan)) 4) "Outdoor manufacturer/model/spacer rows")
  (setq r (garari:test-record (cons '("SOUND" . "あり") base) "4" "1F" master rooms))
  (garari:test-assert (= (garari:get (garari:get r "OUTDOOR") "MODEL") "P-18VSSQD3") "C explicit sound")
  (setq raw (garari:set (garari:set (garari:set (garari:set base "GARARI" "a") "DIA" "100") "FD" "なし") "ROOM" "ｐ-１３ｗｑｕ")
    d (garari:test-record raw "5" "1F" master rooms) plan (garari:table-plan (garari:aggregate (list d)) '("1F")))
  (garari:test-assert (= (garari:get (garari:get d "OUTDOOR") "MODEL") "P-13VSQ4") "D outdoor")
  (garari:test-assert (= (garari:get (garari:get d "INDOOR") "MODEL") "P-13WQU") "D normalized indoor")
  (garari:test-assert (= (nth 5 (nth 1 (car plan))) 1) "D set is one quantity")
  (garari:test-assert (= (length (car plan)) 5) "D indoor on separate row")
  (setq r (garari:test-record (garari:set (garari:set raw "SHAPE" "平型") "ROOM" "なし") "6" "1F" master rooms))
  (garari:test-assert (= (garari:get (garari:get r "OUTDOOR") "MODEL") "BSW100SB10M") "E flat SB")
  (setq r (garari:test-record (garari:set (garari:set base "SHAPE" "平型") "MESH" "なし") "7" "1F" master rooms))
  (garari:test-assert (null (garari:get r "OUTDOOR")) "F unregistered model never fabricated")
  (setq r (garari:test-record (garari:set base "DIA" "100") "8" "1F" master rooms)
    g (garari:aggregate (garari:cross-check (list a r))))
  (garari:test-assert (= (length g) 2) "G same symbol different spec stays separate")
  (garari:test-assert (= (garari:state (cadar g)) "要確認") "G both conflict warning")
  (setq r (garari:test-record (garari:set base "GARARI" "1") "9" "1F" master rooms))
  (garari:test-assert (= (length (garari:aggregate (list a r))) 2) "H symbols separate")
  (setq r (garari:test-record (garari:set base "ROOM" "あり") "10" "1F" master rooms))
  (garari:test-assert (= (garari:state r) "エラー") "I missing indoor model")
  (foreach raw (list (garari:set base "ROOM" "") (garari:set base "DIA" "150×100")
    (garari:set base "FD" "") (vl-remove-if '(lambda (x) (= (car x) "ROOM")) base))
    (setq r (garari:test-record raw "11" "1F" master rooms))
    (garari:test-assert (= (garari:state r) "エラー") "J invalid input retained")
    (garari:test-assert (= (length (garari:aggregate (list r))) 1) "J quantity retained"))
  (setq r (garari:test-record (garari:set base "GARARI" "01") "12" "1F" master rooms))
  (garari:test-assert (= (garari:symbol r) "01") "M leading zeros preserved")
  (setq r (garari:test-record base "13" "1F" (append master master) rooms))
  (garari:test-assert (null (garari:get r "OUTDOOR")) "N multiple approved matches not selected")
  (garari:test-assert (= (garari:state r) "エラー") "N master conflict state")
  (setq r (garari:test-record (garari:set base "ROOM" "P-13WQU") "14" "1F" master rooms))
  (garari:test-assert (= (garari:state r) "エラー") "O indoor dia mismatch")
  (garari:test-assert (null (garari:get r "INDOOR")) "O do not display matched indoor specs")
  (garari:test-assert (equal (garari:floors (mapcar '(lambda (f) (garari:test-record base f f master rooms)) '("other2" "2F" "B1F" "1F" "B2F" "other1" "RF" "階未設定")))
    '("B2F" "B1F" "1F" "2F" "RF" "other2" "other1" "階未設定")) "Floor order including stable unknowns")
  (setq norm (garari:normalize (garari:set base "MATERIAL" "SUS316") garari:config))
  (garari:test-assert (= (garari:get norm "MATERIAL") "SUS316") "Do not replace SUS316")
  (setq r (garari:test-record (garari:set base "GARARI" "") "15" "1F" master rooms))
  (garari:test-assert (= (garari:symbol r) "未設定@15") "Blank symbol surrogate")
  (setq r (garari:test-record (cons '("FLOOR" . "2F") base) "16" "1F" master rooms))
  (garari:test-assert (= (garari:get r "FLOOR") "2F") "FLOOR attribute precedence")
  (garari:test-assert (= (length (car (garari:raw-data (list a)))) (length (cadr (garari:raw-data (list a))))) "CAD_DATA rectangular")
  (princ (strcat "\nGARARITABLETEST PASS=" (itoa garari:test-passed))) (princ))

;; Creates ONLY a dedicated test Excel app and new file in the test directory.
(defun garari:test-write-hidden (path records cfg / garari:config)
  (setq garari:config (garari:set cfg 'show-result nil))
  (garari:write-xlsx path records (garari:aggregate records) (garari:floors records) '(("TEST" "fixture")) nil))
(defun c:GARARITABLECOMTEST (/ *error* garari:stage garari:objects garari:excel garari:book garari:handed garari:temp garari:saved garari:file garari:reason garari:issues master rooms base records path books)
  (defun *error* (msg) (garari:cleanup) (princ (strcat "\nCOMTEST ERROR: " (if garari:stage garari:stage "start") ": " (if garari:reason garari:reason msg))) (princ))
  (setq master (garari:read-master (strcat garari:directory "/garari_master.csv") "outdoor")
    rooms (garari:read-master (strcat garari:directory "/room_master.csv") "room")
    base '(("GARARI" . "01") ("DIA" . "150") ("FD" . "あり") ("SHAPE" . "深型") ("MATERIAL" . "SUS") ("MESH" . "あり") ("ROOM" . "なし")))
  (setq records (list (garari:test-record base "1" "1F" master rooms)
    (garari:test-record base "2" "1F" master rooms) (garari:test-record base "3" "2F" master rooms)
    (garari:test-record (garari:set (garari:set (garari:set base "GARARI" "a") "DIA" "100") "ROOM" "P-13WQU") "4" "1F" master rooms)
    (garari:test-record (garari:set (garari:set base "GARARI" "=1+1") "SHAPE" "平型") "5" "2F" master rooms)))
  (vl-mkdir (strcat garari:directory "/日本語 試験"))
  (setq path (strcat garari:directory "/日本語 試験/acceptance.xlsx"))
  (garari:test-write-hidden path records garari:config)
  (setq books (garari:own (vlax-get-property garari:excel 'Workbooks))
    garari:book (garari:own (garari:open-book books (vl-string-translate "/" "\\" path))))
  (garari:close-book garari:book) (setq garari:book nil)
  (garari:cleanup) (princ "\nGARARITABLECOMTEST PASS") (princ))

;; Only on a disposable empty DWG: creates fixture block GARARI, not production data.
(defun c:GARARITABLECADTEST (/ *error* garari:reason garari:issues garari:file garari:test-passed raw pair tag flag e master rooms r)
  (defun *error* (msg) (if garari:file (close garari:file))
    (princ (strcat "\nCADTEST ERROR: " (if garari:reason garari:reason msg))) (princ))
  (if (tblsearch "BLOCK" "GARARI") (garari:fail "CADTESTはGARARI定義のない検証専用DWGで実行してください。"))
  (setq garari:test-passed 0 raw '(("GARARI" . "2") ("DIA" . "150") ("FD" . "あり") ("SHAPE" . "深型") ("MATERIAL" . "SUS") ("MESH" . "あり") ("ROOM" . "なし")))
  (entmake '((0 . "BLOCK") (2 . "GARARI") (70 . 2) (10 0.0 0.0 0.0)))
  (foreach pair raw
    (setq tag (car pair) flag (cond ((= tag "ROOM") 2) ((= tag "DIA") 1) (T 0)))
    (entmake (list '(0 . "ATTDEF") '(10 0.0 0.0 0.0) '(40 . 2.5) (cons 1 (cdr pair)) (cons 2 tag) (cons 3 tag) (cons 70 flag))))
  (entmake '((0 . "ENDBLK")))
  (entmake '((0 . "INSERT") (2 . "GARARI") (66 . 1) (10 10.0 20.0 0.0)))
  (foreach pair raw
    (if (/= (car pair) "ROOM") (entmake (list '(0 . "ATTRIB") '(10 10.0 20.0 0.0) '(40 . 2.5) (cons 1 (cdr pair)) (cons 2 (car pair)) (cons 70 (if (= (car pair) "DIA") 1 0))))))
  (entmake '((0 . "SEQEND"))) (setq e (entlast))
  (garari:test-assert (garari:target e) "Direct model GARARI is accepted")
  (setq master (garari:read-master (strcat garari:directory "/garari_master.csv") "outdoor") rooms (garari:read-master (strcat garari:directory "/room_master.csv") "room")
    r (garari:extract e "1F" master rooms garari:config))
  (garari:test-assert (= (garari:get (garari:get r "RAW") "DIA") "150") "Invisible DIA read")
  (garari:test-assert (= (garari:get (garari:get r "RAW") "ROOM") "なし") "Constant ROOM read")
  (garari:test-assert (= (garari:get (garari:get r "OUTDOOR") "MODEL") "P-18VSQD4") "Extracted ordinary model")
  (garari:test-assert (= (garari:state r) "正常") "Extracted valid state")
  (garari:test-assert (equal (garari:get r "POINT") '(10.0 20.0 0.0)) "WCS insertion trace")
  (princ (strcat "\nGARARITABLECADTEST PASS=" (itoa garari:test-passed))) (princ))
