;; 10_kikiset.lsp / KIKITABLE.lsp / KIKITABLE_tests.lsp を先にロード。
;; 図面は変更しない。COM試験には実案件ではなくテスト用コピーを渡すこと。
(defun kvt:record (place floor)
  (list '("SYSTEM" . "EF") '("NUM" . "1") (cons "LOCATION" place) (cons "FLOOR" floor)
    '("EQUIP_TYPE" . "ダクト用換気扇") '("MAKER" . "三菱電機") '("MODEL" . "VD-10ZVC7")
    '("TYPE" . "低騒音形 24時間換気機能付 定風量タイプ") '("MOUNT_TYPE" . "天井埋込")
    '("DUCT_DIA" . "100") '("AIRFLOW" . "100") '("STATIC_PRESSURE" . "90")
    '("PHASE" . "1") '("VOLT" . "100") '("POWER" . "0.0097") '("NOISE" . "23.5")))
(defun c:KANKITEST (/ ktt:passed kt:config kt:tags kt:plan kt:warnings records result data ks:category-id)
  (setq ktt:passed 0 kt:config (append kt:vent-config kt:aircon-config)
        kt:tags kt:vent-tags ks:category-id "KANKI")
  (setq data (ks:record-data (cons 3 (append (kvt:record "診察室2" "1") '(("NOTE" . "禁止"))))))
  (foreach tag '("SYSTEM" "NUM" "LOCATION" "FLOOR" "NOTE")
    (ktt:assert (not (assoc tag data)) (strcat "Protected/unlisted: " tag)))
  (ktt:assert (= (length data) 12) "Only twelve ventilation tags")
  (ktt:assert (= (cdr (assoc "PHASE" (ks:record-data '(3 ("PHASE" . "1φ"))))) "1") "Numeric phase")
  (ktt:assert (not (ks:writable-p "POWER" "")) "Empty preserves existing")
  (ktt:assert (= (cadr (kt:vent-spec (kvt:record "A" "1"))) "能力 100φ × 100m3/h × 90Pa") "Vent capacity")
  (ktt:assert (= (cadr (kt:vent-spec '(("DUCT_DIA" . "100") ("AIRFLOW" . "100")))) "能力 100φ × 100m3/h") "Missing pressure")
  (ktt:assert (= (cadr (kt:vent-spec nil)) "") "Empty spec")
  (setq records nil)
  (foreach place '("診察室2" "X線室" "トイレ" "カウンセリングルーム" "院長室" "消毒技工コーナー")
    (setq records (append records (list (kvt:record place "1")))))
  (setq result (kt:plan-vent (kt:group records) '(("1" . 10) ("2" . 11)) 12 13))
  (ktt:assert (equal (car result) '((6 6))) "Six locations use six rows")
  (ktt:assert (= (ktt:planned 6 2) "EF-1") "Derived equipment number")
  (ktt:assert (= (ktt:planned 11 12) 6) "Total at last location")
  (ktt:assert (equal (ktt:planned 6 9) 0.0097 1e-10) "Vent power")
  (setq result (kt:plan-vent (kt:group (append records (list (kvt:record "7" "2") (kvt:record "8" "2")))) '(("1" . 10) ("2" . 11)) 12 13))
  (ktt:assert (equal (car result) '((6 8))) "Eight locations expand")
  (ktt:assert (= (ktt:planned 13 11) 1) "Second floor")
  (setq result (kt:plan-vent (kt:group (list (kvt:record "同室" "1") (kvt:record "同室" "1"))) '(("1" . 10)) 11 12))
  (ktt:assert (= (ktt:planned 6 6) "同室(2)") "Same room grouped")
  (ktt:assert (= (ktt:planned 6 10) 2) "Floor count grouped")
  (ktt:assert (equal (car result) '((6 2))) "Minimum two spec rows")
  (princ (strcat "\nKANKITEST PASSED: " (itoa ktt:passed))) (princ))
(defun kvt:master-test (path / *error* ks:objects ks:excel ks:book ks:stage ks:reason
                           ks:category-id ks:selection-steps kst:answers ktt:passed records selected data model entry)
  (defun *error* (msg) (princ (strcat "\nVENT MASTER FAILED: " (if ks:reason ks:reason msg))) (ks:close-excel) (princ))
  (setq ktt:passed 0 ks:category-id "KANKI" ks:selection-steps ks:vent-steps
        records (ks:read-master path "KANKI_MASTER"))
  (foreach model '("VD-10ZVC7" "VD-15ZLC14-CS" "VD-20ZLC14-S" "VD-23ZLX14-CS" "VD-18ZP14")
    (ktt:assert (ks:filter-records records "MODEL" model) model))
  (setq kst:answers '("三菱電機" "ダクト用換気扇" "100" "100")
        selected (ks:select-record-ui records 'kst:choose) data (ks:record-data selected))
  (ktt:assert (null kst:answers) "Four ventilation choices")
  (foreach entry (ks:record-data (cons 3 (kvt:record "A" "1")))
    (ktt:assert (equal (cdr (assoc (car entry) data)) (cdr entry)) (car entry)))
  (princ (strcat "\nVENT MASTER PASSED: " (itoa ktt:passed))) (princ))
(defun kvt:book-test (path / *error* kt:objects kt:excel kt:book kt:reason kt:stage kt:cell-context kt:log-path
                         kt:config kt:tags kt:raw-tags kt:plan kt:warnings ktt:passed records sheets ws raw ac area i original-count)
  (defun *error* (msg) (princ (strcat "\nVENT BOOK FAILED: " (if kt:reason kt:reason msg))) (kt:cleanup) (princ))
  (setq kt:config (append kt:vent-config kt:aircon-config) kt:tags kt:vent-tags
        kt:raw-tags (kt:raw-columns) ktt:passed 0 records nil)
  (foreach place '("診察室2" "X線室" "トイレ" "カウンセリングルーム" "院長室" "消毒技工コーナー")
    (setq records (append records (list (kvt:record place "1")))))
  (kt:open path)
  (setq sheets (kt:own (vlax-get-property kt:book 'Worksheets)) original-count (vlax-get-property sheets 'Count))
  (kt:write-book records (kt:group records))
  (setq ws (kt:sheet sheets "機器表 (換気設備)") raw (kt:sheet sheets "CAD_DATA_KANKI"))
  (ktt:assert (= (kt:cell-value ws 6 2) "EF-1") "EF-1")
  (ktt:assert (= (kt:cell-value ws 7 5) "能力 100φ × 100m3/h × 90Pa") "Specification")
  (ktt:assert (= (kt:cell-value ws 11 11) 6) "Quantity six")
  (ktt:assert (= (kt:cell-value ws 39 2) "a") "Lower grille table untouched")
  (ktt:assert (= (vlax-get-property sheets 'Count) (1+ original-count)) "Only raw sheet added")
  ;; 40場所で印刷範囲を超え、下部表を上書きせず必要行だけ挿入する。
  (setq records nil i 1)
  (repeat 40 (setq records (cons (kvt:record (strcat "室" (itoa i)) "1") records) i (1+ i)))
  (kt:write-book (reverse records) (kt:group (reverse records)))
  (ktt:assert (= (kt:cell-value ws 45 11) 40) "Forty locations retained")
  (ktt:assert (= (kt:cell-value ws 50 2) "a") "Grille shifted by eleven rows")
  (ktt:assert (= (vlax-get-property sheets 'Count) (1+ original-count)) "Template sheet removed")
  ;; 件数減少時にも古い行が残らない。2階見出しは別の純粋テストで確認。
  (setq records (list (kvt:record "新しい場所" "1")))
  (kt:write-book records (kt:group records))
  (ktt:assert (= (kt:cell-value ws 6 6) "新しい場所") "Rerun location")
  (ktt:assert (null (kt:cell-value ws 9 6)) "Stale location removed")
  (ktt:assert (null (kt:cell-value raw 3 1)) "Stale raw removed")
  (ktt:assert (= (kt:cell-value ws 50 2) "a") "Rerun retains lower table")
  (vlax-invoke-method kt:book 'Save)
  (kt:cleanup)
  (princ (strcat "\nVENT BOOK PASSED: " (itoa ktt:passed))) (princ))
(defun kvt:aircon-book-test (path / *error* kt:objects kt:excel kt:book kt:reason kt:stage kt:cell-context kt:log-path
                               kt:config kt:tags kt:raw-tags kt:plan kt:warnings ktt:passed records sheets ws)
  (defun *error* (msg) (princ (strcat "\nAIRCON BOOK FAILED: " (if kt:reason kt:reason msg))) (kt:cleanup) (princ))
  (setq kt:config kt:aircon-config kt:tags kt:aircon-tags kt:raw-tags (kt:raw-columns) ktt:passed 0
        records (list (ktt:record "PAC-7" "室1" "1" "") (ktt:record "PAC-7" "室2" "1" "")))
  (kt:open path) (kt:write-book records (kt:group records))
  (setq sheets (kt:own (vlax-get-property kt:book 'Worksheets)) ws (kt:sheet sheets "機器表 (空調設備)"))
  (ktt:assert (= (kt:cell-value ws 6 2) "PAC-7") "Aircon number")
  (ktt:assert (= (kt:cell-value ws 8 5) "冷房能力10.0kW　暖房能力11.2kW") "Aircon capacities")
  (ktt:assert (= (kt:cell-value ws 6 7) "3") "Aircon phase")
  (ktt:assert (= (kt:cell-value ws 7 11) 2) "Aircon quantity")
  (vlax-invoke-method kt:book 'Save) (kt:cleanup)
  (princ (strcat "\nAIRCON BOOK PASSED: " (itoa ktt:passed))) (princ))
