;; 本体とKIKISET_MASTER_tests.lspをロード。SharePointは読取りのみ。
(defun c:KIKISETSHARETEST (/ *error* ks:objects ks:excel ks:book ks:download-file ks:reason ks:stage
                          kst:count records again selected start)
  (defun *error* (msg)
    (princ (strcat "\nKIKISETSHARETEST FAILED: " (if ks:reason ks:reason msg)))
    (ks:close-excel) (princ))
  (setq kst:count 0 *ks:master-cache* nil)
  (kst:assert (ks:remote-p (ks:file)) "Default source is HTTPS without selection")
  (setq records (ks:load-master (ks:file) "KANKI_MASTER"))
  (kst:assert (> (length records) 0) "SharePoint records loaded")
  (setq selected (car (ks:filter-records records "MODEL" "VD-10ZVC7")))
  (kst:assert selected "Ventilation model exists")
  (kst:assert (= (ks:record-value selected "POWER") "0.0097") "Remote power value")
  (kst:assert (and (null ks:excel) (null ks:book) (null ks:objects) (null ks:download-file)) "Download and COM cleaned")
  (setq start (getvar "MILLISECS") again (ks:load-master (ks:file) "KANKI_MASTER"))
  (kst:assert (equal records again) "Cached records identical")
  (princ (strcat "\nCACHE milliseconds=" (itoa (- (getvar "MILLISECS") start))))
  (kst:assert (not (equal (ks:cache-key (ks:file) "KANKI_MASTER")
                         (ks:cache-key (ks:file) "KUCHO_KIKI_MASTER"))) "Categories isolated")
  (c:KIKISETRELOAD)
  (kst:assert (null *ks:master-cache*) "Manual reload clears remote cache")
  (princ (strcat "\nKIKISETSHARETEST PASSED: " (itoa kst:count))) (princ))
