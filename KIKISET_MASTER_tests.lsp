;; 10_kikiset.lspを先にロード。KIKISETFILTERTESTは図面・Excelを変更しない。
(defun kst:read-failure (path sheet / ks:objects ks:excel ks:book ks:reason ks:stage result reason)
  (setq result (vl-catch-all-apply 'ks:read-master (list path sheet)) reason ks:reason)
  (ks:close-excel)
  (list (vl-catch-all-error-p result) reason
        (and (null ks:objects) (null ks:excel) (null ks:book))))
(defun kst:error-tests (path / kst:count result)
  (setq kst:count 0 result (kst:read-failure (strcat path ".missing.xlsx") "KUCHO_KIKI_MASTER"))
  (kst:assert (car result) "Missing file fails")
  (kst:assert (vl-string-search "存在しません" (cadr result)) "Missing file reason")
  (kst:assert (caddr result) "Missing file cleanup")
  (setq result (kst:read-failure path "KIKISET_TEST_MISSING_SHEET"))
  (kst:assert (car result) "Missing sheet fails")
  (kst:assert (vl-string-search "シートが存在しません" (cadr result)) "Missing sheet reason")
  (kst:assert (caddr result) "Missing sheet cleanup")
  (princ (strcat "\nKIKISETERRORTEST PASSED: " (itoa kst:count))) (princ))
;; 実マスター試験: (kst:master-test "絶対パス.xlsx" "KUCHO_KIKI_MASTER")
(defun kst:assert (ok label)
  (if ok (setq kst:count (1+ kst:count))
    (progn (princ (strcat "\nFAIL: " label)) (exit))))
(defun kst:choose (title options / answer position)
  (setq answer (car kst:answers) kst:answers (cdr kst:answers))
  (cond ((member answer '(BACK CANCEL)) answer)
        ((numberp answer) answer)
        ((setq position (vl-position answer options)) (1+ position))
        (T (princ (strcat "\nUnexpected choice: " title)) (exit))))
(defun c:KIKISETFILTERTEST (/ kst:count kst:answers ks:stage ks:reason ks:selection-steps
                            headers records selected result numeric)
  (setq kst:count 0)
  (kst:assert (= (ks:value-string 12.5) "12.5") "Numeric 12.5")
  (kst:assert (= (ks:value-string 14.0) "14") "Numeric integer no unit")
  (kst:assert (= (ks:value-string 3.37) "3.37") "Numeric power precision")
  (kst:assert (= (ks:value-string 0.0) "0") "Zero is not empty")
  (kst:assert (= (ks:value-string nil) "") "Empty preserved")
  (kst:assert (= (ks:value-string "001") "001") "Text leading zeros preserved")
  (setq headers (ks:header-map '("COOL_CAP" "MODEL" "MAKER" "SYSTEM")))
  (kst:assert (= (cdr (assoc "MODEL" headers)) 1) "Header mapped by name")
  (setq records (ks:make-records '(("COOL_CAP" "MODEL" "MAKER" "SYSTEM")
                                 ("能力" "型番" "メーカー" "記号")
                                 (12.5 "M-1" "社A" "PAC")
                                 (14 "M-1" "社B" "RAC")
                                 (nil "" "" "")) headers))
  (kst:assert (= (length records) 2) "Blank MODEL row excluded")
  (kst:assert (= (car (cadr records)) 4) "Excel row identity retained")
  (kst:assert (equal (ks:unique-candidates records "MODEL") '("M-1")) "Deduplicate MODEL options")
  (kst:assert (= (length (ks:filter-records records "MAKER" "社B")) 1) "Filter current rows")
  (kst:assert (not (assoc "SYSTEM" (ks:record-data (car records)))) "Protected attribute excluded")
  (kst:assert (= (cdr (assoc "COOL_CAP" (ks:record-data (car records)))) "12.5") "Record to attribute data")
  (kst:assert (equal (ks:unique-candidates records "SERIES") '("")) "Missing classification is blank")
  (kst:assert (= (caar (ks:search-options '("A" "BB" "BC") "b")) 2) "Search keeps source number")
  (kst:assert (equal (ks:unique-candidates '((3 ("SERIES" . "")) (4 ("SERIES" . "ZR"))) "SERIES") '("" "ZR")) "Mixed blanks selectable")
  (setq ks:selection-steps '(("SYSTEM_TYPE" . "種別") ("MAKER" . "メーカー") ("MODEL" . "型番"))
        records '((3 ("SYSTEM_TYPE" . "A") ("MAKER" . "社A") ("MODEL" . "M1"))
                  (4 ("SYSTEM_TYPE" . "A") ("MAKER" . "社B") ("MODEL" . "M2"))
                  (5 ("SYSTEM_TYPE" . "B") ("MAKER" . "社B") ("MODEL" . "M3")))
        kst:answers '("A" BACK "B" "社B" "M3")
        selected (ks:select-record-ui records 'kst:choose))
  (kst:assert (= (car selected) 5) "Back restores rows from previous step")
  (kst:assert (null kst:answers) "All scripted selections consumed")
  (setq kst:answers '("A" CANCEL))
  (kst:assert (null (ks:select-record-ui records 'kst:choose)) "Cancel without a record")
  (setq ks:selection-steps '(("SERIES" . "シリーズ") ("MODEL" . "型番"))
        records '((3 ("MODEL" . "DUP")) (8 ("MODEL" . "DUP")))
        kst:answers '("DUP" BACK "DUP" 2)
        selected (ks:select-record-ui records 'kst:choose))
  (kst:assert (= (car selected) 8) "Duplicate MODEL selected by Excel row")
  (kst:assert (null kst:answers) "Empty step skipped and duplicate back works")
  (setq result (vl-catch-all-apply 'ks:header-map (list '("MAKER"))))
  (kst:assert (vl-catch-all-error-p result) "Missing MODEL detected")
  (setq result (vl-catch-all-apply 'ks:header-map (list '("MODEL" " model "))))
  (kst:assert (vl-catch-all-error-p result) "Duplicate normalized header detected")
  (setq result (vl-catch-all-apply 'ks:make-records (list '(("MODEL") ("型番")) '(("MODEL" . 0)))))
  (kst:assert (vl-catch-all-error-p result) "No equipment rows detected")
  (princ (strcat "\nKIKISETFILTERTEST PASSED: " (itoa kst:count))) (princ))

(defun kst:master-test (path sheet / *error* ks:objects ks:excel ks:book ks:stage ks:reason
                         kst:count kst:answers records selected expected entry headers values rebuilt names model started cached)
  (defun *error* (msg)
    (princ (strcat "\nKIKISETMASTERTEST FAILED: " (if ks:reason ks:reason msg)))
    (ks:close-excel) (princ))
  (setq *ks:master-cache* nil kst:count 0 records (ks:load-master path sheet))
  (setq started (getvar "MILLISECS") cached (ks:load-master path sheet))
  (princ (strcat "\nCACHE milliseconds=" (itoa (- (getvar "MILLISECS") started))))
  (kst:assert (equal records cached) "Cache returns same records")
  (kst:assert (equal (car *ks:master-cache*) (ks:cache-key path sheet)) "Cache fingerprint")
  (kst:assert (not (equal (car *ks:master-cache*) (ks:cache-key path "OTHER"))) "Sheet invalidates cache")
  (kst:assert (null (ks:cache-key (strcat path ".missing") sheet)) "Missing file cannot use cache")
  (kst:assert (and (null ks:objects) (null ks:excel) (null ks:book)) "Excel closed before selection")
  (foreach model '("PLZ-ZRMP140HF6" "PLZX-ERMP224H6" "PLZT-ERMP224L6" "PLZX-ZRMP280HF6-M" "PLZX-ZRMP140L6")
    (kst:assert (ks:filter-records records "MODEL" model) (strcat "Registered MODEL: " model)))
  (setq kst:answers '("三菱電機" "2方向天井カセット形" "同時ツイン" "140")
        selected (ks:select-record-ui records 'kst:choose))
  (kst:assert (null kst:answers) "All four actual classification choices")
  (setq expected '(("MODEL" . "PLZX-ZRMP140L6") ("COOL_CAP" . "12.5") ("HEAT_CAP" . "14")
                   ("COOL_POWER" . "3.37") ("HEAT_POWER" . "3.96")
                   ("INDOOR_MODEL" . "PL-RP71LA22") ("OUTDOOR_MODEL" . "PUZ-ZRMP140KA16")
                   ("INDOOR_QTY" . "2") ("REMOTE_MODEL" . "PAR-48MA")
                   ("LIQ_PIPE" . "9.52") ("GAS_PIPE" . "15.88")))
  (foreach entry expected
    (kst:assert (= (ks:record-value selected (car entry)) (cdr entry)) (car entry)))
  ;; 同じ実データから列を逆順にしてヘッダー変換・レコード再生成を試験する。
  (setq names (reverse (mapcar 'car (cdr selected)))
        headers (ks:header-map names)
        values (mapcar '(lambda (key) (cdr (assoc key (cdr selected)))) names)
        rebuilt (ks:make-record (car selected) values headers))
  (foreach entry expected
    (kst:assert (= (ks:record-value rebuilt (car entry)) (cdr entry)) (strcat "Reordered " (car entry))))
  (princ (strcat "\nKIKISETMASTERTEST PASSED: " (itoa kst:count)
                 " / Excel row=" (itoa (car selected)) " / MODEL=" (ks:record-value selected "MODEL")))
  (ks:close-excel) (princ))
