;; Requires garari_regression.lsp and disposable fixtures created by the test runner.
(setq garari:config (garari:set garari:config 'show-result nil))
(defun gt:update (path records / garari:stage garari:objects garari:excel garari:book garari:handed garari:temp garari:saved garari:file garari:reason result)
  (setq result (vl-catch-all-apply 'garari:write-xlsx
    (list path records (garari:aggregate records) '("1F" "2F" "3F" "4F") '(("TEST" "yes")) nil)))
  (setq gt:excel-started (not (null garari:excel)) gt:stage garari:stage)
  (garari:cleanup)
  (if (vl-catch-all-error-p result)
    (progn
      (setq gt:file (open (strcat garari:directory "/com-error.txt") "w" "utf8"))
      (write-line (strcat "stage=" (if garari:stage garari:stage "nil") " / " (if garari:reason garari:reason (vl-catch-all-error-message result))) gt:file)
      (close gt:file)
      (princ (strcat "\nCOM_ERROR: " (if garari:reason garari:reason (vl-catch-all-error-message result))))))
  result)
(setq gt:path (strcat garari:directory "/fixture.xlsx"))
(setq gt:backup (garari:backup-path gt:path))
(gt:assert (garari:copy-backup gt:path gt:backup) "backup-copy-saved-bytes")
(gt:assert (= (vl-file-size gt:path) (vl-file-size gt:backup)) "backup-size-verified")
(gt:assert (not (garari:copy-backup gt:path gt:backup)) "backup-existing-file-not-overwritten")
(gt:assert (and garari:backup-error (/= garari:backup-error "")) "backup-copy-error-detail")
(gt:assert (not (garari:copy-backup (strcat garari:directory "/missing.xlsx") (garari:backup-path gt:path))) "backup-missing-source-refused")
(setq gt:r2 (garari:set gt:r150 "HANDLE" "B2"))
(setq gt:r2 (garari:set gt:r2 "FLOOR" "2F"))
(gt:assert (not (vl-catch-all-error-p (gt:update gt:path (list gt:r150 gt:r2)))) "existing-excel-first-update")
(gt:assert (not (vl-catch-all-error-p (gt:update gt:path (list gt:r150)))) "existing-excel-replace-not-add")
(gt:assert (not (vl-catch-all-error-p (gt:update (strcat garari:directory "/offset.xlsx") (list gt:r150)))) "template-offset-preserved")
(gt:assert (vl-catch-all-error-p (gt:update (strcat garari:directory "/locked.xlsx") (list gt:r150))) "readonly-excel-refused")
(defun garari:copy-backup (path backup) nil)
(gt:assert (vl-catch-all-error-p (gt:update (strcat garari:directory "/backupfail.xlsx") (list gt:r150))) "backup-failure-no-write")
(defun garari:copy-backup (path backup) (garari:copy-backup-file path backup))
(gt:assert (vl-catch-all-error-p (gt:update (strcat garari:directory "/busy.xlsx") (list gt:r150))) "busy-file-refused")
(setq gt:owner-path (strcat garari:directory "/ownerbusy.xlsx"))
(setq gt:file (open (garari:owner-file gt:owner-path) "w"))
(write-line "disposable owner-file fixture" gt:file) (close gt:file)
(gt:assert (vl-catch-all-error-p (gt:update gt:owner-path (list gt:r150))) "owner-file-refused")
(gt:assert (not gt:excel-started) "owner-file-refused-before-excel-start")
(gt:assert (= gt:stage "対象ファイルのロック確認") "owner-file-preflight-stage")
(gt:assert (findfile (garari:owner-file gt:owner-path)) "owner-file-not-deleted")
(vl-file-delete (garari:owner-file gt:owner-path))
(princ (strcat "\nGARARI_EXCEL_REGRESSION_OK=" (itoa gt:count)))
(princ)
